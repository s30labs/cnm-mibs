-------------------------------------------------------------------------------
-- IT Assistant MIB : itassist.mib 
-- 
-- Copyright (c) 2004-2005 Dell Inc. 
-- All Rights Reserved. 
-- 
-- The information and functionality described by this MIB file, 
-- like many MIB files, is subject to change without notice. 
-- Please examine the version number of this MIB and compare it 
-- to the version number you are expecting. 
-- 
-- MIB Version 1.0                      25 June 2003 
-- 
--
-------------------------------------------------------------------------------


-------------------------------------------------------------------------------
-- Begin MIB
-------------------------------------------------------------------------------

MIB-Dell-10900 DEFINITIONS ::= BEGIN

IMPORTS
    enterprises, IpAddress
        FROM RFC1155-SMI
    OBJECT-TYPE
        FROM RFC-1212
    TRAP-TYPE
        FROM RFC-1215
    DisplayString
        FROM RFC1213-MIB;


-------------------------------------------------------------------------------
-- Object Identifiers
-------------------------------------------------------------------------------

-- Enterprise ID
dell                            OBJECT IDENTIFIER ::= { enterprises    674   }

-- IT Assistant
itAssistant                         OBJECT IDENTIFIER ::= { dell           10900 }
itAssistantTrap                  OBJECT IDENTIFIER ::= { itAssistant        1     }

-------------------------------------------------------------------------------
--
-- MIB Groups
--
-------------------------------------------------------------------------------

DellString                      ::= DisplayString (SIZE (0..512))
DellString1                      ::= DisplayString (SIZE (0..128))
-------------------------------------------------------------------------------
-- MIB Version Group
--
-- OID Format: 1.3.6.1.4.1.674.10892.1.1.<a>.0
-------------------------------------------------------------------------------

itaAlertMessage                           OBJECT-TYPE
    SYNTAX      DellString
    ACCESS      read-only
    STATUS      mandatory
    DESCRIPTION
"Message in the alert."
    ::= { itAssistantTrap 1 }
itaAlertNode                           OBJECT-TYPE
    SYNTAX      DellString
    ACCESS      read-only
    STATUS      mandatory
    DESCRIPTION
"Name of the node where alert originated."
    ::= { itAssistantTrap 2 }
itaAlertSeverity                 OBJECT-TYPE 
      SYNTAX         DellString1 
      ACCESS         read-only 
      STATUS         mandatory 
      DESCRIPTION 
				"Original severity of the alert." 
      ::= { itAssistantTrap 3 } 
itaAlertCounterName              OBJECT-TYPE 
	SYNTAX         DellString 
      ACCESS         read-only 
      STATUS         mandatory 
      DESCRIPTION 
					"Name of the counter for which alert is generated." 
      ::= { itAssistantTrap 4 }
itaAlertThresholdOperator              OBJECT-TYPE 
	SYNTAX         DellString 
      ACCESS         read-only 
      STATUS         mandatory 
      DESCRIPTION 
					"Name of the threshold operator." 
      ::= { itAssistantTrap 5 }
itaAlertThresholdValue              OBJECT-TYPE 
	SYNTAX         DellString1
      ACCESS         read-only 
      STATUS         mandatory 
      DESCRIPTION 
					"Threshold value." 
      ::= { itAssistantTrap 6 }
itaAlertThresholdCount              OBJECT-TYPE 
	SYNTAX         DellString1
      ACCESS         read-only 
      STATUS         mandatory 
      DESCRIPTION 
					"Threshold count." 
      ::= { itAssistantTrap 7 }
-------------------------------------------------------------------------------
--
-- Traps
--
-------------------------------------------------------------------------------


-------------------------------------------------------------------------------
-- Miscellaneous Traps
-------------------------------------------------------------------------------

itaAlertSystemUp                                   TRAP-TYPE
    ENTERPRISE  itAssistantTrap
    VARIABLES { itaAlertMessage,
                itaAlertNode }
    DESCRIPTION
"System up message from IT Assistant. Sent when IT Assistant detects a node has come online."

    --Novell NMS trap annotation
    --#TYPE       "Server Battery Failure"
    --#SUMMARY    "%s"
    --#ARGUMENTS  {2}
    --#SEVERITY   CRITICAL
    --#TIMEINDEX  99
    --#STATE      DEGRADED
    --#CATEGORY			"Status Events"
    ::= 1000

itaAlertSystemDown               TRAP-TYPE 
      ENTERPRISE  itAssistantTrap 
      VARIABLES  { itaAlertMessage, itaAlertNode } 
      DESCRIPTION 
"System down message from IT Assistant. Sent when IT Assistant detects a node has gone offline." 
      ---Novell NMS trap annotation 
      --#TYPE				"System Down Message from IT Assistant" 
      --#SUMMARY			"%s: %s" 
      --#ARGUMENTS			{0,1} 
      --#SEVERITY			CRITICAL 
      --#TIMEINDEX			99 
      --#STATE				NONOPERATIONAL 
      --#CATEGORY			"Error Events" 
      ::= 1001 
 
itaAlertForwardedAlert           TRAP-TYPE 
      ENTERPRISE  itAssistantTrap 
      VARIABLES  { itaAlertMessage, itaAlertNode, itaAlertSeverity } 
      DESCRIPTION 
"Forwarded alert from IT Assistant. The event may have originated from an SNMP trap, DMI indication, or CIM indication." 
      ---Novell NMS trap annotation 
      --#TYPE				"Forwarded Alert from IT Assistant" 
      --#SUMMARY			"Forwarded Alert from IT Assistant. Sending node: %s, Severity: %s, Message: %s." 
      --#ARGUMENTS			{1,2,0} 
      --#SEVERITY			INFORMATIONAL 
      --#TIMEINDEX			99 
      --#STATE				OPERATIONAL 
      --#CATEGORY			"Status Events"
	::= 2000

itaAlertSystemMonitoringCriticalAlert                 TRAP-TYPE 
      ENTERPRISE  itAssistantTrap 
      VARIABLES  { itaAlertCounterName, itaAlertThresholdOperator, itaAlertThresholdValue, itaAlertThresholdCount } 
      DESCRIPTION 
		"System monitoring alert from IT Assistant. Sent when a node's system monitoring counters has exceeded user defined critical threshold." 
      --Novell NMS trap annotation 
      --#TYPE				"System monitoring alert from IT Assistant" 
      --#SUMMARY			"%s was %s %s for %s consecutive samples." 
      --#ARGUMENTS			{0,1,2,3} 
      --#SEVERITY			CRITICAL 
      --#TIMEINDEX			99 
      --#STATE				OPERATIONAL 
      --#CATEGORY			"Error Events" 
      ::= 3001

itaAlertSystemMonitoringWarningAlert                 TRAP-TYPE 
      ENTERPRISE  itAssistantTrap 
      VARIABLES  { itaAlertCounterName, itaAlertThresholdOperator, itaAlertThresholdValue, itaAlertThresholdCount } 
      DESCRIPTION 
		"System monitoring alert from IT Assistant. Sent when a node's system monitoring counters has exceeded user defined warning threshold."
      --Novell NMS trap annotation 
      --#TYPE				"System monitoring alert from IT Assistant" 
      --#SUMMARY			"%s was %s %s for %s consecutive samples." 
      --#ARGUMENTS			{0,1,2,3} 
      --#SEVERITY			WARNING 
      --#TIMEINDEX			99 
      --#STATE				OPERATIONAL 
      --#CATEGORY			"Status Events" 
      ::= 3002

itaAlertCPUMonitoringCriticalAlert                 TRAP-TYPE 
      ENTERPRISE  itAssistantTrap 
      VARIABLES  { itaAlertCounterName, itaAlertThresholdOperator, itaAlertThresholdValue, itaAlertThresholdCount } 
      DESCRIPTION 
		"CPU monitoring alert from IT Assistant. Sent when a node's CPU utilization has exceeded user defined critical threshold." 
      --Novell NMS trap annotation 
      --#TYPE				"CPU monitoring alert from IT Assistant" 
      --#SUMMARY			"%s was %s %s for %s consecutive samples." 
      --#ARGUMENTS			{0,1,2,3} 
      --#SEVERITY			CRITICAL 
      --#TIMEINDEX			99 
      --#STATE				OPERATIONAL 
      --#CATEGORY			"Error Events" 
      ::= 3003

itaAlertCPUMonitoringWarningAlert                 TRAP-TYPE 
      ENTERPRISE  itAssistantTrap 
      VARIABLES  { itaAlertCounterName, itaAlertThresholdOperator, itaAlertThresholdValue, itaAlertThresholdCount } 
      DESCRIPTION 
		"CPU monitoring alert from IT Assistant. Sent when a node's CPU utilization has exceeded user defined warning threshold." 
      --Novell NMS trap annotation 
      --#TYPE				"CPU monitoring alert from IT Assistant" 
      --#SUMMARY			"%s was %s %s for %s consecutive samples." 
      --#ARGUMENTS			{0,1,2,3} 
      --#SEVERITY			WARNING 
      --#TIMEINDEX			99 
      --#STATE				OPERATIONAL 
      --#CATEGORY			"Status Events" 
      ::= 3004

itaAlertMemoryMonitoringCriticalAlert                 TRAP-TYPE 
      ENTERPRISE  itAssistantTrap 
      VARIABLES  { itaAlertCounterName, itaAlertThresholdOperator, itaAlertThresholdValue, itaAlertThresholdCount } 
      DESCRIPTION 
		"Memory monitoring alert from IT Assistant. Sent when a node's memory utilization has exceeded user defined critical threshold." 
      --Novell NMS trap annotation 
      --#TYPE				"Memory monitoring alert from IT Assistant" 
      --#SUMMARY			"%s was %s %s for %s consecutive samples." 
      --#ARGUMENTS			{0,1,2,3} 
      --#SEVERITY			CRITICAL 
      --#TIMEINDEX			99 
      --#STATE				OPERATIONAL 
      --#CATEGORY			"Error Events" 
      ::= 3005

itaAlertMemoryMonitoringWarningAlert                 TRAP-TYPE 
      ENTERPRISE  itAssistantTrap 
      VARIABLES  { itaAlertCounterName, itaAlertThresholdOperator, itaAlertThresholdValue, itaAlertThresholdCount } 
      DESCRIPTION 
		"Memory monitoring alert from IT Assistant. Sent when a node's memory utilization has exceeded user defined warning threshold." 
      --Novell NMS trap annotation 
      --#TYPE				"Memory monitoring alert from IT Assistant" 
      --#SUMMARY			"%s was %s %s for %s consecutive samples." 
      --#ARGUMENTS			{0,1,2,3} 
      --#SEVERITY			WARNING 
      --#TIMEINDEX			99 
      --#STATE				OPERATIONAL 
      --#CATEGORY			"Status Events" 
      ::= 3006

itaAlertNetworkMonitoringCriticalAlert                 TRAP-TYPE 
      ENTERPRISE  itAssistantTrap 
      VARIABLES  { itaAlertCounterName, itaAlertThresholdOperator, itaAlertThresholdValue, itaAlertThresholdCount } 
      DESCRIPTION 
		"Network monitoring alert from IT Assistant. Sent when a node's NIC utilization has exceeded user defined critical threshold." 
      --Novell NMS trap annotation 
      --#TYPE				"Network monitoring alert from IT Assistant" 
      --#SUMMARY			"%s was %s %s for %s consecutive samples." 
      --#ARGUMENTS			{0,1,2,3} 
      --#SEVERITY			CRITICAL 
      --#TIMEINDEX			99 
      --#STATE				OPERATIONAL 
      --#CATEGORY			"Error Events" 
      ::= 3007

itaAlertNetworkMonitoringWarningAlert                 TRAP-TYPE 
      ENTERPRISE  itAssistantTrap 
      VARIABLES  { itaAlertCounterName, itaAlertThresholdOperator, itaAlertThresholdValue, itaAlertThresholdCount } 
      DESCRIPTION 
		"Network monitoring alert from IT Assistant. Sent when a node's NIC utilization has exceeded user defined warning threshold." 
      --Novell NMS trap annotation 
      --#TYPE				"Network monitoring alert from IT Assistant" 
      --#SUMMARY			"%s was %s %s for %s consecutive samples." 
      --#ARGUMENTS			{0,1,2,3} 
      --#SEVERITY			WARNING 
      --#TIMEINDEX			99 
      --#STATE				OPERATIONAL 
      --#CATEGORY			"Status Events" 
      ::= 3008

itaAlertPhysicalDiskMonitoringCriticalAlert                 TRAP-TYPE 
      ENTERPRISE  itAssistantTrap 
      VARIABLES  { itaAlertCounterName, itaAlertThresholdOperator, itaAlertThresholdValue, itaAlertThresholdCount } 
      DESCRIPTION 
		"Physical disk monitoring alert from IT Assistant. Sent when a node's physical disk utilization has exceeded user defined critical threshold." 
      --Novell NMS trap annotation 
      --#TYPE				"Physical disk monitoring alert from IT Assistant" 
      --#SUMMARY			"%s was %s %s for %s consecutive samples." 
      --#ARGUMENTS			{0,1,2,3} 
      --#SEVERITY			CRITICAL 
      --#TIMEINDEX			99 
      --#STATE				OPERATIONAL 
      --#CATEGORY			"Error Events" 
      ::= 3009

itaAlertPhysicalDiskMonitoringWarningAlert                 TRAP-TYPE 
      ENTERPRISE  itAssistantTrap 
      VARIABLES  { itaAlertCounterName, itaAlertThresholdOperator, itaAlertThresholdValue, itaAlertThresholdCount } 
      DESCRIPTION 
		"Physical disk monitoring alert from IT Assistant. Sent when a node's Physical disk utilization has exceeded user defined warning threshold." 
      --Novell NMS trap annotation 
      --#TYPE				"Physical disk monitoring alert from IT Assistant" 
      --#SUMMARY			"%s was %s %s for %s consecutive samples." 
      --#ARGUMENTS			{0,1,2,3} 
      --#SEVERITY			WARNING 
      --#TIMEINDEX			99 
      --#STATE				OPERATIONAL 
      --#CATEGORY			"Status Events" 
      ::= 3010

itaAlertLogicalDiskMonitoringCriticalAlert                 TRAP-TYPE 
      ENTERPRISE  itAssistantTrap 
      VARIABLES  { itaAlertCounterName, itaAlertThresholdOperator, itaAlertThresholdValue, itaAlertThresholdCount } 
      DESCRIPTION 
		"Logical disk monitoring alert from IT Assistant. Sent when a node's logical disk utilization has exceeded user defined critical threshold." 
      --Novell NMS trap annotation 
      --#TYPE				"Logical disk monitoring alert from IT Assistant" 
      --#SUMMARY			"%s was %s %s for %s consecutive samples." 
      --#ARGUMENTS			{0,1,2,3} 
      --#SEVERITY			CRITICAL 
      --#TIMEINDEX			99 
      --#STATE				OPERATIONAL 
      --#CATEGORY			"Error Events" 
      ::= 3011

itaAlertLogicalDiskMonitoringWarningAlert                 TRAP-TYPE 
      ENTERPRISE  itAssistantTrap 
      VARIABLES  { itaAlertCounterName, itaAlertThresholdOperator, itaAlertThresholdValue, itaAlertThresholdCount } 
      DESCRIPTION 
		"Logical disk monitoring alert from IT Assistant. Sent when a node's Logical disk utilization has exceeded user defined warning threshold." 
      --Novell NMS trap annotation 
      --#TYPE				"Logical disk monitoring alert from IT Assistant" 
      --#SUMMARY			"%s was %s %s for %s consecutive samples." 
      --#ARGUMENTS			{0,1,2,3} 
      --#SEVERITY			WARNING 
      --#TIMEINDEX			99 
      --#STATE				OPERATIONAL 
      --#CATEGORY			"Status Events" 
      ::= 3012
END

-------------------------------------------------------------------------------
-- End MIB
-------------------------------------------------------------------------------
