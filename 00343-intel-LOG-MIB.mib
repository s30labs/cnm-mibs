INTEL-LOG-MIB DEFINITIONS ::= BEGIN

-- Copyright (C) 1997 Intel Corporation. All rights reserved.
--
-- log MIB, 1998-11-30
--
-- Proprietary MIB containing information about the Log System.
--
-- Build 1

--

IMPORTS
    TimeTicks                  FROM RFC1155-SMI
    mib2ext                    FROM INTEL-GEN-MIB
    OBJECT-TYPE                FROM RFC-1212
    DisplayString              FROM RFC1213-MIB;

    log                OBJECT IDENTIFIER ::= { mib2ext 8 }
    logInfo            OBJECT IDENTIFIER ::= { log 1 }

logListTable OBJECT-TYPE
    SYNTAX SEQUENCE OF LogListEntry
    ACCESS not-accessible
    STATUS mandatory
    DESCRIPTION ""
    ::= { logInfo 1 }

logListEntry OBJECT-TYPE
    SYNTAX LogListEntry
    ACCESS not-accessible
    STATUS mandatory
    DESCRIPTION ""
    INDEX { logListSeqno }
    ::= { logListTable 1 }

LogListEntry ::= SEQUENCE {
                        logListSeqno
                           OCTET STRING,
                        logListCode
                           INTEGER,
                        logListSource
                           INTEGER,
                        logListCategory
                           OCTET STRING,
                        logListLevel
                           INTEGER,
                        logListTimeStamp
                           TimeTicks,
                        logListMulti
                           OCTET STRING,
                        logListText1
                           DisplayString (SIZE(250)),
                        logListText2
                           DisplayString (SIZE(250)),
                        logListText3
                           DisplayString (SIZE(250)),
                        logListText4
                           DisplayString (SIZE(250)),
                        logListChassis
                           INTEGER,
                        logListModule
                           INTEGER,
                        logListPort
                           INTEGER,
                        logListExtFlags
                           INTEGER,
                        logListRepeats
                           Counter
                        }

logListSeqno OBJECT-TYPE
    SYNTAX OCTET STRING (SIZE(8))
    ACCESS read-only
    STATUS mandatory
    DESCRIPTION ""
    ::= { logListEntry 1 }

logListCode OBJECT-TYPE
    SYNTAX INTEGER
    ACCESS read-only
    STATUS mandatory
    DESCRIPTION "Unique identifier (combination of Source and ID: upper two
    bytes are source and lower to bytes are ID)"
    ::= { logListEntry 2 }

logListSource OBJECT-TYPE
    SYNTAX INTEGER {
    misc(1),
    system(2),
    syslogd(3),
    ipx(6),
    ip(7),
    isdn(8),
    callcontrol(9),
    framerelay(10),
    ppp(11),
    link(12),
    tunnel(13),
    x25(14),
    csu(15),
    hdlc(16),
    wanPort(17),
    modem(18),
    ipm(19),
    rsvp(20),
    l3l(21),
    ipru(22),
    gmrp(23),
    lapb(24),
    bridging(25)
    }
    ACCESS read-only
    STATUS mandatory
    DESCRIPTION ""
    ::= { logListEntry 3 }

logListCategory OBJECT-TYPE
    SYNTAX OCTET STRING (SIZE(8))
    ACCESS read-only
    STATUS mandatory
    DESCRIPTION "Max 64 categories"
    ::= { logListEntry 4 }

logListLevel OBJECT-TYPE
    SYNTAX INTEGER {
              fatalError(100),
              error(70),
              warning(60),
              note(50),
              info(40),
              debug(30)
             }
    ACCESS read-only
    STATUS mandatory
    DESCRIPTION ""
    ::= { logListEntry 5 }

logListTimeStamp OBJECT-TYPE
    SYNTAX TimeTicks
    ACCESS read-only
    STATUS mandatory
    DESCRIPTION "time in secs since 1970-1-1"
    ::= { logListEntry 6 }

logListMulti OBJECT-TYPE
    SYNTAX OCTET STRING (SIZE(64))
    ACCESS read-only
    STATUS mandatory
    DESCRIPTION "code(4) category(8) level(2) timestamp(4) repeats(2).
                (code(4) = source(2) + Id(2))
                Number in parenthesis is number of bytes used by element."
    ::= { logListEntry 7 }

logListText1 OBJECT-TYPE
    SYNTAX DisplayString (SIZE(250))
    ACCESS read-only
    STATUS mandatory
    DESCRIPTION "Text1, Text2, Text3 and Text4 should be concatenated to give the description string."
    ::= { logListEntry 8 }

logListText2 OBJECT-TYPE
    SYNTAX DisplayString (SIZE(250))
    ACCESS read-only
    STATUS mandatory
    DESCRIPTION ""
    ::= { logListEntry 9 }

logListText3 OBJECT-TYPE
    SYNTAX DisplayString (SIZE(250))
    ACCESS read-only
    STATUS mandatory
    DESCRIPTION ""
    ::= { logListEntry 10 }

logListText4 OBJECT-TYPE
    SYNTAX DisplayString (SIZE(250))
    ACCESS read-only
    STATUS mandatory
    DESCRIPTION ""
    ::= { logListEntry 11 }

logListChassis OBJECT-TYPE
    SYNTAX INTEGER
    ACCESS read-only
    STATUS mandatory
    DESCRIPTION ""
    ::= { logListEntry 12 }

logListModule OBJECT-TYPE
    SYNTAX INTEGER
    ACCESS read-only
    STATUS mandatory
    DESCRIPTION ""
    ::= { logListEntry 13 }

logListPort OBJECT-TYPE
    SYNTAX INTEGER
    ACCESS read-only
    STATUS mandatory
    DESCRIPTION ""
    ::= { logListEntry 14 }

logListExtFlags OBJECT-TYPE
    SYNTAX INTEGER
    ACCESS read-write
    STATUS mandatory
    DESCRIPTION ""
    ::= { logListEntry 15 }

logListRepeats OBJECT-TYPE
    SYNTAX Counter
    ACCESS read-only
    STATUS mandatory
    DESCRIPTION "Number of times this message text has been inserted."
    ::= { logListEntry 16 }

logArgListTable OBJECT-TYPE
    SYNTAX SEQUENCE OF LogArgListEntry
    ACCESS not-accessible
    STATUS mandatory
    DESCRIPTION ""
    ::= { logInfo 2 }

logArgListEntry OBJECT-TYPE
    SYNTAX LogArgListEntry
    ACCESS not-accessible
    STATUS mandatory
    DESCRIPTION ""
    INDEX { logArgListSeqno, logArgListArgNumber }
    ::= { logArgListTable 1 }

LogArgListEntry ::= SEQUENCE {
                        logArgListSeqno
                           OCTET STRING,
                        logArgListArgNumber
                           OCTET STRING,
                        logArgListArg
                           DisplayString (SIZE(255))
                        }

logArgListSeqno OBJECT-TYPE
    SYNTAX OCTET STRING (SIZE(8))
    ACCESS read-only
    STATUS mandatory
    DESCRIPTION ""
    ::= { logArgListEntry 1 }

logArgListArgNumber OBJECT-TYPE
    SYNTAX OCTET STRING (SIZE(1))
    ACCESS read-only
    STATUS mandatory
    DESCRIPTION ""
    ::= { logArgListEntry 2 }

logArgListArg OBJECT-TYPE
    SYNTAX DisplayString (SIZE(255))
    ACCESS read-only
    STATUS mandatory
    DESCRIPTION "The first byte is the datatype ('s':string) and the rest of the value is the argument"
    ::= { logArgListEntry 3 }

logMgmtTable OBJECT-TYPE
    SYNTAX SEQUENCE OF LogMgmtEntry
    ACCESS not-accessible
    STATUS mandatory
    DESCRIPTION ""
    ::= { logInfo 3 }

logMgmtEntry OBJECT-TYPE
    SYNTAX LogMgmtEntry
    ACCESS not-accessible
    STATUS mandatory
    DESCRIPTION ""
    INDEX { logMgmtIpAddress }
    ::= { logMgmtTable 1 }

LogMgmtEntry ::= SEQUENCE {
                        logMgmtIpAddress
                           OCTET STRING,
                        logMgmtSeqno
                           OCTET STRING
                        }

logMgmtIpAddress OBJECT-TYPE
    SYNTAX OCTET STRING (SIZE(4))
    ACCESS read-only
    STATUS mandatory
    DESCRIPTION ""
    ::= { logMgmtEntry 1 }

logMgmtSeqno OBJECT-TYPE
    SYNTAX OCTET STRING (SIZE(8))
    ACCESS read-write
    STATUS mandatory
    DESCRIPTION "External mgmt stations can write a seqno to store how far they have come in reading the log."
    ::= { logMgmtEntry 2 }

logListEntryCount OBJECT-TYPE
    SYNTAX INTEGER
    ACCESS read-write
    STATUS mandatory
    DESCRIPTION "Write 0 to this value clears the log."
    ::= { logInfo 4 }

logListFirstSeqno OBJECT-TYPE
    SYNTAX OCTET STRING (SIZE(8))
    ACCESS read-only
    STATUS mandatory
    DESCRIPTION ""
    ::= { logInfo 5 }

logListLastSeqno OBJECT-TYPE
    SYNTAX OCTET STRING (SIZE(8))
    ACCESS read-only
    STATUS mandatory
    DESCRIPTION ""
    ::= { logInfo 6 }

logListLastUpdateTime OBJECT-TYPE
    SYNTAX TimeTicks
    ACCESS read-only
    STATUS mandatory
    DESCRIPTION "Last insertion in log in timeticks since boot"
    ::= { logInfo 7 }

END
