CTRON-AP3000-MIB DEFINITIONS ::= BEGIN

IMPORTS
    ifIndex                                 	FROM RFC1213-MIB
    mgmt,Counter,IpAddress, enterprises     	FROM RFC1155-SMI
    MODULE-IDENTITY, NOTIFICATION-TYPE, OBJECT-TYPE, Integer32, Counter32, TimeTicks
                                          	FROM SNMPv2-SMI
    DisplayString,RowStatus, TruthValue, TEXTUAL-CONVENTION, MacAddress
        					FROM SNMPv2-TC
    ;
    --PhysAddress		::= OCTET STRING
    --Guage32			::= Counter
    --MacAddress		::= OCTET STRING
    --DisplayString		::= OCTET STRING
    --TruthValue		::=
    --INTEGER { false(2), true(1) }
    cabletron		OBJECT IDENTIFIER ::= { enterprises 52 }
    mibs 		OBJECT IDENTIFIER ::= { cabletron 4 }


ctronAP3000 MODULE-IDENTITY
    LAST-UPDATED "200404200755Z"  -- Mon Apr  12 08:45 GMT 2004
    ORGANIZATION "Enterasys Networks, Inc"
    CONTACT-INFO
    "Postal: Enterasys Networks
             35 Industrial Way, P.O. Box 5005
             Rochester, NH 03867-0505

     Phone:  +1 603 332 9400
     E-mail: support@enterasys.com
     WWW:    http://www.enterasys.com"
   
     DESCRIPTION
        "This mib module defines a portion of the SNMP enterprise
         MIBs under Enterasys Networks enterprise OID as an extension 
         to the Enterasys AP3000 MIB.
         
         This Enterasys Networks Proprietary MIB was designed to be 
         used for read-write access to configuration objects in AP3000."

            
    
    REVISION "200409010947Z"  -- Tues. September 01 09:47 GMT 2004
    DESCRIPTION
       "1. May 06,04, add the texcual deinition not_supported(2) in apRadioSecurityWPAMode in SYNTAX.
        2. May 06,04, add 3's group :apEtherInterfaceMgnt,apVLANMgnt,apAuthenticationMgnt.
		3. June 24,04,
			-Add three elements(.1--.3) into apSecurityMgnt.apSecuritySsh 
			-Add two elements into apAuthenticationMgnt.apAuthenticationServerTable.apAuthenticationServerEntry as
				apAuthenticationAcctPort  INTEGER 
    			apAuthenticationAcctInterimUpdate   INTEGER
			-Add four elements(.13--.16) into apRadioInterfaceMgnt.apRadioInterfaceTable.apRadioInterfaceEntry
			-Add apRogueApMgnt.
		4. July 05,04,
			-Add apFilterControlMgnt.
			-Add apWStationSessionMgnt.
			-Add apAdminMgnt.
			-Add apResetMgt.
			-Add apSNTPMgnt.
			-Add apDNSMgnt.
			-Add apIappMgnt.
			-Add apSyslogMgnt.
			-Add apEventLogMgnt.
			-Add one element-apMacFilterControl(.2) into macFilterMgnt.
			-Rename 'snmpTrapMgnt' with 'apSnmpMgnt' with change the oid.
			-Deprecate the trapDot11InterfaceAGFail	in 	apSnmpMgnt.trapConfiguration.
			-Add the trapDot11InterfaceAFail(.21) into apSnmpMgnt.trapConfiguration.
			-Add the trapDot11InterfaceGFail(.22) into apSnmpMgnt.trapConfiguration.
			-Add the three objects into apSnmpMgnt.
				-the apSnmpTrapDestinationTable(.3)
				-the apSnmpCommunityReadOnly(.4)
				-the apSnmpCommunityReadWrite(.5)
			-Add the dot11InterfaceAFail(.21) into apNotificationTrapObjects.
			-Add the dot11InterfaceGFail(.22) into apNotificationTrapObjects.
			-Add the dot11InterfaceAFail(.21) into apNotificationTrapObjects.
			-Deprecate the apInterfaceVlanId_A in apVLANMgnt.
			-Deprecate the apInterfaceVlanId_G in apVLANMgnt.
			-Add the apNativeVlanTable into apVLANMgnt.					 
		5.July 05,04
			-Remove the Object deifnition-dot11InterfaceAGFail in apFilterControlMgnt.in apNotificationTrapTree.apNotificationTrapObjects.
			-Add qosQueueingMode in qosMgnt.
		6.July 22,04
			-Add apWStationSessionVlanID in qosMgnt.apWStationSessionTable.apWStationSessionEntry.
		7.August 30,04
			-replace 'ENTERASYS-AP3000-PRIVATE-MIB' with 'CTRON-AP3000-MIB'
			-Remove the object definition-'rogueApAuthenticate INTEGER' which is not implemented.
			-Fix some syntax error.
		8.September 01,04
			-Add rogueApRADIUSAuthenticate into  apRogueApMgnt.apRougeApControl.
       "


    ::= { mibs 13 }
   
-- -------------------------------------------------------------
-- groups in the ENTERASYS-AP3000-PRIVATE-MIB 
-- -------------------------------------------------------------
	comPortMgnt				OBJECT IDENTIFIER ::= { ctronAP3000 1 }
	macFilterMgnt			OBJECT IDENTIFIER ::= { ctronAP3000 2 }
	qosMgnt					OBJECT IDENTIFIER ::= { ctronAP3000 3 }
	linkQualityMgnt			OBJECT IDENTIFIER ::= { ctronAP3000 4 }
--	snmpTrapMgnt			OBJECT IDENTIFIER ::= { ctronAP3000 5 }
	apSnmpMgnt				OBJECT IDENTIFIER ::= { ctronAP3000 5 }
	sysEntity				OBJECT IDENTIFIER ::= { ctronAP3000 6 }
	apSecurityMgnt			OBJECT IDENTIFIER ::= { ctronAP3000 7 }
	apRadioInterfaceMgnt	OBJECT IDENTIFIER ::= { ctronAP3000 8 }
	apEtherInterfaceMgnt	OBJECT IDENTIFIER ::= { ctronAP3000 9 }
	apFilterControlMgnt		OBJECT IDENTIFIER ::= { ctronAP3000 10 }
	apVLANMgnt				OBJECT IDENTIFIER ::= { ctronAP3000 11 }
	apAuthenticationMgnt	OBJECT IDENTIFIER ::= { ctronAP3000 12 }	
	apWStationSessionMgnt	OBJECT IDENTIFIER ::= { ctronAP3000 13 }	
	apRogueApMgnt          	OBJECT IDENTIFIER ::= { ctronAP3000 14 }
	apAdminMgnt          	OBJECT IDENTIFIER ::= { ctronAP3000 15 }
	apResetMgt          	OBJECT IDENTIFIER ::= { ctronAP3000 16 }
	apSNTPMgnt          	OBJECT IDENTIFIER ::= { ctronAP3000 17 }
	apDNSMgnt          		OBJECT IDENTIFIER ::= { ctronAP3000 18 }
	apIappMgnt          	OBJECT IDENTIFIER ::= { ctronAP3000 19 }
	apSyslogConfigMgnt		OBJECT IDENTIFIER ::= { ctronAP3000 20 }
	apEventLogMgnt     		OBJECT IDENTIFIER ::= { ctronAP3000 21 }
	apNotificationTrapTree	OBJECT IDENTIFIER ::= { ctronAP3000 100 }

-- -------------------------------------------------------------
-- Textual Conventions
-- -------------------------------------------------------------
-- tbd
-- -------------------------------------------------------------
-- START::The apFilterControlMgnt Group
-- -------------------------------------------------------------	
apFilterControlBridge OBJECT-TYPE
	    SYNTAX     INTEGER
               {
                   enabled(1),
                   disabled(2)
               }
        MAX-ACCESS read-write
        STATUS current
        DESCRIPTION
            "This value indicates the local bridge filter setting."
        ::= { apFilterControlMgnt 1 }

enterpriseApFilterControlAPManage OBJECT-TYPE
	    SYNTAX     INTEGER
               {
                   enabled(1),
                   disabled(2)
               }
        MAX-ACCESS read-write
        STATUS current
        DESCRIPTION
            "This value indicates the AP management filter setting."
        ::= { apFilterControlMgnt 2 }

enterpriseApFilterControlEthernet OBJECT-TYPE
	    SYNTAX     INTEGER
               {
                   enabled(1),
                   disabled(2)
               }
        MAX-ACCESS read-write
        STATUS current
        DESCRIPTION
            "This value indicates the ethernet filter setting."
        ::= { apFilterControlMgnt 3 }

enterpriseApFilterProtocolTable OBJECT-TYPE
        SYNTAX      SEQUENCE OF EnterpriseApFilterProtocolEntry
        MAX-ACCESS  not-accessible
        STATUS      current
        DESCRIPTION "Table of descriptive and status information about
                     configuration of the filter protocol table."
        ::= { apFilterControlMgnt 4 }

enterpriseApFilterProtocolEntry OBJECT-TYPE
        SYNTAX      EnterpriseApFilterProtocolEntry
        MAX-ACCESS  not-accessible
        STATUS      current
        DESCRIPTION "An entry in the filter protocol table, containing information
                     about configuration of one filter table entry."
        INDEX       { enterpriseApFilterProtocolIndex }
        ::= { enterpriseApFilterProtocolTable 1 }

EnterpriseApFilterProtocolEntry ::= SEQUENCE
{
    enterpriseApFilterProtocolIndex          Integer32,
    enterpriseApFilterProtocolName           DisplayString,
    enterpriseApFilterProtocolISODesignator  DisplayString,
    enterpriseApFilterProtocolState          INTEGER
}

enterpriseApFilterProtocolIndex OBJECT-TYPE
        SYNTAX      Integer32
        MAX-ACCESS  not-accessible
        STATUS      current
        DESCRIPTION "Index of the Protocol Filters."
        ::= { enterpriseApFilterProtocolEntry 1 }

enterpriseApFilterProtocolName OBJECT-TYPE
        SYNTAX DisplayString
        MAX-ACCESS read-only
        STATUS current
        DESCRIPTION
            "This value indicates the name of the protocol filter.  One of 
			 the following:
			 Aironet_DDP, Appletalk_ARP, ARP, Banyan, Berkeley_Trailer_Negotiation, 
			 CDP, DEC_LAT, DEC_MOP, DEC_MOP_Dump_Load, DEC_XNS, EAPOL, 
			 Enet_Config_Test, Ethertalk, IP, LAN_Test, NetBEUI, Novell_IPX(new),
			 Novell_IPX(old), RARP, Telxon_TXP, X.25_Level3
			"
    ::= { enterpriseApFilterProtocolEntry 2 }

enterpriseApFilterProtocolISODesignator OBJECT-TYPE
        SYNTAX DisplayString
        MAX-ACCESS read-only
        STATUS current
        DESCRIPTION
            "This value indicates the name of the protocol filter."
    ::= { enterpriseApFilterProtocolEntry 3 }

enterpriseApFilterProtocolState OBJECT-TYPE
	    SYNTAX     INTEGER
               {
                   enabled(1),
                   disabled(2)
               }
        MAX-ACCESS read-write
        STATUS current
        DESCRIPTION
            "This value indicates whether the protocol filter is enabled."
    ::= { enterpriseApFilterProtocolEntry 4 }
-- -------------------------------------------------------------
-- End::The apFilterControlMgnt Group
-- -------------------------------------------------------------

-- -------------------------------------------------------------
-- START::The ComPortMgnt Group
-- -------------------------------------------------------------	
comPortControl OBJECT-TYPE
    SYNTAX INTEGER { enabled(1), disabled(2) }
    MAX-ACCESS read-write
    STATUS current
    DESCRIPTION
    "The administrative enable/disable state for
     COM Port Control in a System."
::= { comPortMgnt 1 }  
-- -------------------------------------------------------------
-- End::The ComPortMgnt Group
-- -------------------------------------------------------------
          
-- -------------------------------------------------------------
-- START::The macFilterMgnt Group
-- -------------------------------------------------------------
macFilterTable OBJECT-TYPE
        SYNTAX      SEQUENCE OF MacFilterEntry
        ACCESS      not-accessible
        STATUS      mandatory
        DESCRIPTION "Table of status information about
                     each configured MAC Filtering Entry."
        ::= { macFilterMgnt 1 }

macFilterEntry OBJECT-TYPE
        SYNTAX      MacFilterEntry
        ACCESS      not-accessible
        STATUS      mandatory
        DESCRIPTION "An entry in the table, containing information
                     about configuration of MAC Filter."
        INDEX       { macFilterIndex }
        ::= { macFilterTable 1 }

MacFilterEntry ::= SEQUENCE
{
    macFilterIndex                        Integer32,
    macFilterAddress                      MacAddress,
    macFilterAllowedToGo		  INTEGER,
    macFilterOpeStatus                    INTEGER
}

macFilterIndex OBJECT-TYPE
        SYNTAX      Integer32
        ACCESS      not-accessible
        STATUS      mandatory
        DESCRIPTION "Filter index."
        ::= { macFilterEntry 1 }


macFilterAddress OBJECT-TYPE
        SYNTAX MacAddress
        ACCESS read-write
        STATUS mandatory
        DESCRIPTION
            "This values indicates the MAC address of the 
            MAC Filter entry."
    ::= { macFilterEntry 2 }

macFilterAllowedToGo OBJECT-TYPE
    SYNTAX INTEGER { allow(1), deny(2) }
    MAX-ACCESS read-write
    STATUS current
    DESCRIPTION
    "The administrative allow/deny state for
     that specificed MAC Filter Entry."
::= { macFilterEntry 3 }            

macFilterOpeStatus OBJECT-TYPE
        SYNTAX INTEGER{
                    other(0),
                    vaild(1),
                    invalid(2),
                    create(3)
                }

        ACCESS read-create
        STATUS mandatory
        DESCRIPTION
        "This object indicates the status of this entry.
            other(0) - this entry is currently in use but
                the conditions under which it will remain
                so differ from the following values.
            valid(1) - this value to indicate this entry is currently 
            	in used. 
            invalid(2) - write this value to the corresponding entry,
            	the whole entry will be removed. Since the order of entry 
            	shall be re-order while it has been deleted. To re-freshed
            	the whole table is recommended for new index.
            create(3) - wirte this value to indicate that the new mac address
            	will be added after next writing mac address to that new entry.
            	The adding action will be taked on the index that grater than 1.
         " 
 
    DEFVAL      { permanent }

    ::= { macFilterEntry 4 }
-- -------------------------------------------------------------
apMacFilterControl OBJECT-TYPE
	    SYNTAX     INTEGER
               {
                   enabled(1),
                   disabled(2)
               }
        MAX-ACCESS read-write
        STATUS current
        DESCRIPTION
            "This value indicates the control of the MAC filter setting."
        ::= { macFilterMgnt 2 }    
-- -------------------------------------------------------------
-- END::The macFilterMgnt Group
-- -------------------------------------------------------------


-- -------------------------------------------------------------
-- START::The qosMgnt Group
-- -------------------------------------------------------------
qosModeControl OBJECT-TYPE
    SYNTAX INTEGER
       {
          qosoff(1),
          qossa(2),
          qosda(3),
          qosether(4),
          qos8021p(5)
       }
    MAX-ACCESS read-write
    STATUS current
    DESCRIPTION
    "The administrative status and control of the QOS mode for the QOS management."
::= { qosMgnt 1 }         

qosMACTypeTable OBJECT-TYPE
        SYNTAX      SEQUENCE OF QosMACTypeEntry
        ACCESS      not-accessible
        STATUS      mandatory
        DESCRIPTION "Table of status information about
                     each configured MAC Type Entry for the QoS Management."
        ::= { qosMgnt 2 }

qosMACTypeEntry OBJECT-TYPE
        SYNTAX      QosMACTypeEntry
        ACCESS      not-accessible
        STATUS      mandatory
        DESCRIPTION "An entry in the table, containing information
                     about configuration MAC Type Entry for the QoS Management."
        INDEX       { qosMACTypeIndex }
        ::= { qosMACTypeTable 1 }

QosMACTypeEntry ::= SEQUENCE
{
    qosMACTypeIndex			Integer32,
    qosMACTypeAddress			MacAddress,
    qosMACTypePriority			Integer32,
    qosMACTypeOpeStatus			INTEGER
}

qosMACTypeIndex OBJECT-TYPE
        SYNTAX      Integer32
        ACCESS      not-accessible
        STATUS      mandatory
        DESCRIPTION "Qos MAC Type index."
        ::= { qosMACTypeEntry 1 }


qosMACTypeAddress OBJECT-TYPE
        SYNTAX MacAddress
        ACCESS read-write
        STATUS mandatory
        DESCRIPTION
            "This values indicates the MAC address of that specified  
            index in the entry."
    ::= { qosMACTypeEntry 2 }

qosMACTypePriority OBJECT-TYPE
        SYNTAX Integer32 (0..7)
        ACCESS read-write
        STATUS mandatory
        DESCRIPTION
            "This values indicates the level of priority of that specified 
            MAC Address in  entry."

    ::= { qosMACTypeEntry 3 }

qosMACTypeOpeStatus OBJECT-TYPE
        SYNTAX INTEGER{
                    other(0),
                    vaild(1),
                    invalid(2),
                    create(3)
                }

        ACCESS read-create
        STATUS mandatory
        DESCRIPTION
        "This object indicates the status of this entry.
            other(0) - this entry is currently in use but
                the conditions under which it will remain
                so differ from the following values.
            valid(1) - this value to indicate this entry is currently 
            	in used. 
            invalid(2) - write this value to the corresponding entry,
            	the whole entry will be removed. Since the order of entry 
            	shall be re-order while it has been deleted. To re-freshed
            	the whole table is recommended for new index.
            create(3) - wirte this value to indicate that the new mac address
            	will be added after next writing mac address to that new entry.
            	The adding action will be taked on the index that grater than 1.
          " 
    DEFVAL      { permanent }

    ::= { qosMACTypeEntry 4 }

qosEtherTypeTable OBJECT-TYPE
        SYNTAX      SEQUENCE OF QosEtherTypeEntry
        ACCESS      not-accessible
        STATUS      mandatory
        DESCRIPTION "Table of status information about
                     each configured Ether Type Entry for QoS Management."
        ::= { qosMgnt 3 }

qosEtherTypeEntry OBJECT-TYPE
        SYNTAX      QosEtherTypeEntry
        ACCESS      not-accessible
        STATUS      mandatory
        DESCRIPTION "An entry in the table, containing information
                     about configration Ether Type for QoS Management."
        INDEX       { qosMACTypeIndex }
        ::= { qosEtherTypeTable 1 }

QosEtherTypeEntry ::= SEQUENCE
{
    qosEtherTypeIndex                        	Integer32,
    qosEtherTypeHexValue			OCTET STRING,
    qosEtherTypePriority                     	Integer32,
    qosEtherTypeOpeStatus			INTEGER
}

qosEtherTypeIndex OBJECT-TYPE
        SYNTAX      Integer32
        ACCESS      not-accessible
        STATUS      mandatory
        DESCRIPTION "Qos Ether Type index in the table."
        ::= { qosEtherTypeEntry 1 }


qosEtherTypeHexValue OBJECT-TYPE
        SYNTAX OCTET STRING (SIZE(4))
        ACCESS read-write
        STATUS mandatory
        DESCRIPTION
            "The Hex Value to indicate the type of Ether of that specified  
            index in the entry."
    ::= { qosEtherTypeEntry 2 }

qosEtherTypePriority OBJECT-TYPE
        SYNTAX Integer32 (0..7)
        ACCESS read-write
        STATUS mandatory
        DESCRIPTION
            "This values indicates the level of priority of that specified 
            MAC Address in  entry."

    ::= { qosEtherTypeEntry 3 }

qosEtherTypeOpeStatus OBJECT-TYPE
        SYNTAX INTEGER{
                    other(0),
                    vaild(1),
                    invalid(2),
                    create(3)
                }

        ACCESS read-create
        STATUS mandatory
        DESCRIPTION
        "This object indicates the status of this entry.
            other(0) - this entry is currently in use but
                the conditions under which it will remain
                so differ from the following values.
            valid(1) - this value to indicate this entry is currently 
            	in used. 
            invalid(2) - write this value to the corresponding entry,
            	the whole entry will be removed. Since the order of entry 
            	shall be re-order while it has been deleted. To re-freshed
            	the whole table is recommended for new index.
            create(3) - wirte this value to indicate that the new Ether Value
            	will be added after next writing Ether Type Value to that new entry.
            	The adding action will be taked on the index that grater than 1.
          " 
    DEFVAL      { permanent }

    ::= { qosEtherTypeEntry 4 }

qosQueueingMode OBJECT-TYPE
    SYNTAX INTEGER { weightted-fair(1),
                     strict-priority(2)
    }
    MAX-ACCESS read-write
    STATUS current
    DESCRIPTION
    "The administrative control of the QOS Queueing mode for the QOS management."
::= { qosMgnt 4 }     

-- -------------------------------------------------------------
-- END::The qosMgnt Group
-- -------------------------------------------------------------


-- -------------------------------------------------------------
-- START::The linkQualityMgnt Group
-- -------------------------------------------------------------
linkQualityTable OBJECT-TYPE
        SYNTAX      SEQUENCE OF LinkQualityEntry
        ACCESS      not-accessible
        STATUS      mandatory
        DESCRIPTION "Table of status information about
                     the radio Interface Link Quality Entry."
        ::= { linkQualityMgnt 1 }

linkQualityEntry OBJECT-TYPE
        SYNTAX      LinkQualityEntry
        ACCESS      not-accessible
        STATUS      mandatory
        DESCRIPTION "An entry in the table, containing information
                     about configuration of  the radio Interface Link Quality."
        INDEX		{ linkQualityRadioIndex,
        	 	  linkQualityStaIndex }

        ::= { linkQualityTable 1 }

LinkQualityEntry ::= SEQUENCE
{
    linkQualityRadioIndex		Integer32,
    linkQualityStaIndex			Integer32,
    linkQualityStaMacAddress      	MacAddress,
    linkQualityStaRssi               	Integer32
}
linkQualityRadioIndex OBJECT-TYPE
        SYNTAX      Integer32
        ACCESS      not-accessible
        STATUS      mandatory
        DESCRIPTION "This is the value to define the index 
        of the radio interface." 
        ::= { linkQualityEntry 1 }

linkQualityStaIndex OBJECT-TYPE
        SYNTAX      Integer32
        ACCESS      not-accessible
        STATUS      mandatory
        DESCRIPTION "This is value to define the index 
        of link station."
        ::= { linkQualityEntry 2 }

linkQualityStaMacAddress OBJECT-TYPE
        SYNTAX MacAddress
        ACCESS read-only
        STATUS mandatory
        DESCRIPTION
            "This values indicates the MAC address of the 
            link station."
    ::= { linkQualityEntry 3 }

linkQualityStaRssi OBJECT-TYPE
        SYNTAX Integer32(0..100)
        ACCESS read-only
        STATUS mandatory
        DESCRIPTION
            "This values indicates the percentage RSSI of the 
            link station."
    ::= { linkQualityEntry 4 }
-- -------------------------------------------------------------
-- END::The linkQualityMgnt Group
-- -------------------------------------------------------------

-- -------------------------------------------------------------
-- START::The snmpTrapMgnt-apSnmpMgnt Group
-- -------------------------------------------------------------	
trapControl OBJECT-TYPE
    SYNTAX INTEGER { enabled(1), disabled(2) }
    MAX-ACCESS read-write
    STATUS current
    DESCRIPTION
    "The administrative enable/disable state for
     SNMP Trap Control in a System."
--::= { snmpTrapMgnt 1 }   
::= { apSnmpMgnt 1 }   
-- -------------------------------------------------------------
--trapConfiguration     OBJECT IDENTIFIER ::= { snmpTrapMgnt 2 }
trapConfiguration     OBJECT IDENTIFIER ::= { apSnmpMgnt 2 }
--01   trapSysSystemUp                 Enable/Disable sysSystemUp trap
--02   trapSysSystemDown               Enable/Disable sysSystemDown trap
--03   trapSysRadiusServerChanged      Enable/Disable sysRadiusServerChanged trap
--04   trapDot11StationAssociation     Enable/Disable dot11StationAssociation trap
--05   trapDot11StationReAssociation   Enable/Disable dot11StationReAssociation trap
--06   trapDot11StationAuthentication  Enable/Disable dot11StationAuthentication trap
--07   trapDot11StationRequestFail     Enable/Disable dot11StationRequestFail trap
--08   trapDot11InterfaceAGFail        Enable/Disable dot11InterfaceAGFail trap
--09   trapLocalMacAddrAuthFail        Enable/Disable localMacAddrAuthFail trap
--10   trapLocalMacAddrAuthSuccess     Enable/Disable localMacAddrAuthSuccess trap
--11   trapDot1xAuthNotInitiated       Enable/Disable dot1xAuthNotInitiated trap
--12   trapDot1xAuthSuccess            Enable/Disable dot1xAuthSuccess trap
--13   trapDot1xAuthFail               Enable/Disable dot1xAuthFail trap
--14   trapDot1xMacAddrAuthSuccess     Enable/Disable dot1xMacAddrAuthSuccess trap
--15   trapDot1xMacAddrAuthFail        Enable dot1xMacAddrAuthFail trap
--16   trapPppLogonFail                Enable/Disable pppLogonFail trap
--17   trapIappStationRoamedFrom       Enable/Disable iappStationRoamedFrom trap
--18   trapIappStationRoamedTo         Enable/Disable iappStationRoamedTo trap
--19   trapIappContextDataSent         Enable iappContextDataSent trap
--20   trapSntpServerFail              Enable/Disable sntpServerFail trap


trapSysSystemUp OBJECT-TYPE
    SYNTAX INTEGER { enabled(1), disabled(2) }
    MAX-ACCESS read-write
    STATUS current
    DESCRIPTION
    "The administrative enable/disable state for
     SNMP sysSystemUp trap."
::= { trapConfiguration 1 }  

trapSysSystemDown OBJECT-TYPE
    SYNTAX INTEGER { enabled(1), disabled(2) }
    MAX-ACCESS read-write
    STATUS current
    DESCRIPTION
    "The administrative enable/disable state for
     SNMP sysSystemDown trap."
::= { trapConfiguration 2 }   

trapSysRadiusServerChanged OBJECT-TYPE
    SYNTAX INTEGER { enabled(1), disabled(2) }
    MAX-ACCESS read-write
    STATUS current
    DESCRIPTION
    "The administrative enable/disable state for
     SNMP sysRadiusServerChanged trap."
::= { trapConfiguration 3 }  

 trapDot11StationAssociation OBJECT-TYPE
    SYNTAX INTEGER { enabled(1), disabled(2) }
    MAX-ACCESS read-write
    STATUS current
    DESCRIPTION
    "The administrative enable/disable state for
     SNMP dot11StationAssociation trap."
::= { trapConfiguration 4 }   

 trapDot11StationReAssociation OBJECT-TYPE
    SYNTAX INTEGER { enabled(1), disabled(2) }
    MAX-ACCESS read-write
    STATUS current
    DESCRIPTION
    "The administrative enable/disable state for
     SNMP dot11StationReAssociation trap."
::= { trapConfiguration 5 }  

trapDot11StationAuthentication OBJECT-TYPE
    SYNTAX INTEGER { enabled(1), disabled(2) }
    MAX-ACCESS read-write
    STATUS current
    DESCRIPTION
    "The administrative enable/disable state for
     SNMP dot11StationAuthentication trap."
::= { trapConfiguration 6 }   

trapDot11StationRequestFail OBJECT-TYPE
    SYNTAX INTEGER { enabled(1), disabled(2) }
    MAX-ACCESS read-write
    STATUS current
    DESCRIPTION
    "The administrative enable/disable state for
     SNMP dot11StationRequestFail trap."
::= { trapConfiguration 7 }  

-- trapDot11InterfaceAGFail OBJECT-TYPE
--    SYNTAX INTEGER { enabled(1), disabled(2) }
--    MAX-ACCESS read-write
--    STATUS current
--    DESCRIPTION
--    "The administrative enable/disable state for
--     SNMP dot11InterfaceAGFail trap."
--::= { trapConfiguration 8 }   

trapLocalMacAddrAuthFail OBJECT-TYPE
    SYNTAX INTEGER { enabled(1), disabled(2) }
    MAX-ACCESS read-write
    STATUS current
    DESCRIPTION
    "The administrative enable/disable state for
     SNMP localMacAddrAuthFail trap."
::= { trapConfiguration 9 }   

trapLocalMacAddrAuthSuccess OBJECT-TYPE
    SYNTAX INTEGER { enabled(1), disabled(2) }
    MAX-ACCESS read-write
    STATUS current
    DESCRIPTION
    "The administrative enable/disable state for
     SNMP localMacAddrAuthSuccess trap."
::= { trapConfiguration 10 }      

trapDot1xAuthNotInitiated OBJECT-TYPE
    SYNTAX INTEGER { enabled(1), disabled(2) }
    MAX-ACCESS read-write
    STATUS current
    DESCRIPTION
    "The administrative enable/disable state for
     SNMP dot1xAuthNotInitiated trap."
::= { trapConfiguration 11 }

trapDot1xAuthSuccess OBJECT-TYPE
    SYNTAX INTEGER { enabled(1), disabled(2) }
    MAX-ACCESS read-write
    STATUS current
    DESCRIPTION
    "The administrative enable/disable state for
     SNMP dot1xAuthSuccess trap."
::= { trapConfiguration 12 }      

trapDot1xAuthFail OBJECT-TYPE
    SYNTAX INTEGER { enabled(1), disabled(2) }
    MAX-ACCESS read-write
    STATUS current
    DESCRIPTION
    "The administrative enable/disable state for
     SNMP  dot1xAuthFail trap."
::= { trapConfiguration 13 }

trapDot1xMacAddrAuthSuccess OBJECT-TYPE
    SYNTAX INTEGER { enabled(1), disabled(2) }
    MAX-ACCESS read-write
    STATUS current
    DESCRIPTION
    "The administrative enable/disable state for
     SNMP dot1xMacAddrAuthSuccess trap."
::= { trapConfiguration 14 }      

trapDot1xMacAddrAuthFail OBJECT-TYPE
    SYNTAX INTEGER { enabled(1), disabled(2) }
    MAX-ACCESS read-write
    STATUS current
    DESCRIPTION
    "The administrative enable/disable state for
     SNMP dot1xMacAddrAuthFail trap."
::= { trapConfiguration 15 }

trapPppLogonFail OBJECT-TYPE
    SYNTAX INTEGER { enabled(1), disabled(2) }
    MAX-ACCESS read-write
    STATUS current
    DESCRIPTION
    "The administrative enable/disable state for
     SNMP pppLogonFail trap."
::= { trapConfiguration 16 }      

trapIappStationRoamedFrom OBJECT-TYPE
    SYNTAX INTEGER { enabled(1), disabled(2) }
    MAX-ACCESS read-write
    STATUS current
    DESCRIPTION
    "The administrative enable/disable state for
     SNMP iappStationRoamedFrom trap."
::= { trapConfiguration 17 }     

trapIappStationRoamedTo OBJECT-TYPE
    SYNTAX INTEGER { enabled(1), disabled(2) }
    MAX-ACCESS read-write
    STATUS current
    DESCRIPTION
    "The administrative enable/disable state for
     SNMP iappStationRoamedFrom trap."
::= { trapConfiguration 18 }     

trapIappContextDataSent OBJECT-TYPE
    SYNTAX INTEGER { enabled(1), disabled(2) }
    MAX-ACCESS read-write
    STATUS current
    DESCRIPTION
    "The administrative enable/disable state for
     SNMP iappContextDataSent trap."
::= { trapConfiguration 19 }      

trapSntpServerFail OBJECT-TYPE
    SYNTAX INTEGER { enabled(1), disabled(2) }
    MAX-ACCESS read-write
    STATUS current
    DESCRIPTION
    "The administrative enable/disable state for
     SNMP sntpServerFail trap."
::= { trapConfiguration 20 }  

trapDot11InterfaceAFail OBJECT-TYPE
    SYNTAX INTEGER { enabled(1), disabled(2) }
    MAX-ACCESS read-write
    STATUS current
    DESCRIPTION
    "The administrative enable/disable state for
     SNMP dot11InterfaceAFail trap."
::= { trapConfiguration 21 }  

trapDot11InterfaceGFail OBJECT-TYPE
    SYNTAX INTEGER { enabled(1), disabled(2) }
    MAX-ACCESS read-write
    STATUS current
    DESCRIPTION
    "The administrative enable/disable state for
     SNMP dot11InterfaceGFail trap."
::= { trapConfiguration 22 }  
-- -------------------------------------------------------------
apSnmpTrapDestinationTable OBJECT-TYPE
        SYNTAX      SEQUENCE OF ApSnmpTrapDestinationEntry
        MAX-ACCESS  not-accessible
        STATUS      current
        DESCRIPTION "Table of descriptive and status information about
                     configuration of each trap receiving server."
    ::= { apSnmpMgnt 3 }

apSnmpTrapDestinationEntry OBJECT-TYPE
        SYNTAX      ApSnmpTrapDestinationEntry
        MAX-ACCESS  not-accessible
        STATUS      current
        DESCRIPTION "An entry in the table, containing information
                     about configuration of one trap receiving server."
        INDEX       { apSnmpTrapDestinationIndex }
        ::= { apSnmpTrapDestinationTable 1 }

ApSnmpTrapDestinationEntry ::= SEQUENCE
{
    apSnmpTrapDestinationIndex        INTEGER,
    apSnmpTrapDestinationCommunity    DisplayString,
    apSnmpTrapDestinationIP           IpAddress,
    apSnmpTrapDestinationState        INTEGER
}

apSnmpTrapDestinationIndex OBJECT-TYPE
        SYNTAX      INTEGER (1..4) 
        MAX-ACCESS  not-accessible
        STATUS      current
        DESCRIPTION "Index of the Trap Destination Table."
        ::= { apSnmpTrapDestinationEntry 1 }

apSnmpTrapDestinationCommunity OBJECT-TYPE
        SYNTAX     DisplayString (SIZE(0..32))
        MAX-ACCESS read-write
        STATUS current
        DESCRIPTION
            "The SNMP Trap Community"
        ::= { apSnmpTrapDestinationEntry 2 }

apSnmpTrapDestinationIP OBJECT-TYPE
        SYNTAX IpAddress
        MAX-ACCESS read-write
        STATUS current
        DESCRIPTION
            "The IP address of the trap receiving server."
        ::= { apSnmpTrapDestinationEntry 3 }

apSnmpTrapDestinationState OBJECT-TYPE
	SYNTAX INTEGER
               {
                   enabled(1),
                   disabled(2)
               }
        MAX-ACCESS read-write
        STATUS current
        DESCRIPTION
            "This value indicates whether the trap receiving server is enabled."
        ::= { apSnmpTrapDestinationEntry 4 }
-- -------------------------------------------------------------
apSnmpCommunityReadOnly OBJECT-TYPE
    SYNTAX     DisplayString (SIZE(0..32))
    MAX-ACCESS read-write
    STATUS     current
    DESCRIPTION "The SNMP Read Only Community.  The value if read,
	             will only show ******."
    ::= { apSnmpMgnt 4 }

apSnmpCommunityReadWrite OBJECT-TYPE
    SYNTAX     DisplayString (SIZE(0..32))
    MAX-ACCESS read-write
    STATUS     current
    DESCRIPTION "The SNMP Read Write Community.  The value if read,
	             will only show *****."
    ::= { apSnmpMgnt 5 }
    
-- -------------------------------------------------------------
-- END::The snmpTrapMgnt Group
-- -------------------------------------------------------------

-- -------------------------------------------------------------
--  START::sysEntity - Standard Mib elements
-- -------------------------------------------------------------
swHardwareVer OBJECT-TYPE
        SYNTAX      DisplayString (SIZE (0..20))
        MAX-ACCESS  read-only
        STATUS      current
        DESCRIPTION "Hardware version of the main board."
        ::= { sysEntity 1 }

swBootRomVer OBJECT-TYPE
        SYNTAX      DisplayString (SIZE(0..20))
        MAX-ACCESS  read-only
        STATUS      current
        DESCRIPTION "Boot ROM code version of the main board."
        ::= { sysEntity 2 }

swOpCodeVer OBJECT-TYPE
        SYNTAX      DisplayString (SIZE(0..20))
        MAX-ACCESS  read-only
        STATUS      current
        DESCRIPTION "Operation code version of the main board."
        ::= { sysEntity 3 }

swSerialNumber OBJECT-TYPE
        SYNTAX      DisplayString (SIZE(0..20))
        MAX-ACCESS  read-only
        STATUS      current
        DESCRIPTION "Serial Number of the Access Point."
        ::= { sysEntity 4 }

-- resetConfigurationMgnt     OBJECT IDENTIFIER ::= { sysEntity 5 }
-- -------------------------------------------------------------
--  END::sysEntity - Standard Mib elements
-- -------------------------------------------------------------


-- -------------------------------------------------------------
-- - apRadioSecurityMgnt TABLE
-- -------------------------------------------------------------
apRadioSecurityTable OBJECT-TYPE
        SYNTAX      SEQUENCE OF ApRadioSecurityEntry
        MAX-ACCESS  not-accessible
        STATUS      current
        DESCRIPTION "Table of descriptive and status information about
                     configuration of each radio in terms of security settings."
        ::= { apSecurityMgnt 1 }

apRadioSecurityEntry OBJECT-TYPE
        SYNTAX      ApRadioSecurityEntry
        MAX-ACCESS  not-accessible
        STATUS      current
        DESCRIPTION "An entry in the table, containing information
                     about configuration of one radio of the AP."
        INDEX       { apRadioSecurityIndex }
        ::= { apRadioSecurityTable 1 }

ApRadioSecurityEntry ::= SEQUENCE
{
    apRadioSecurityIndex     Integer32,
    apRadioSecurityWEPAuthType    INTEGER,
    apRadioSecuritySharedKeyLen   INTEGER,
    apRadioSecurityWPAMode        INTEGER,
    apRadioSecurityWPAKeyType     INTEGER,
    apRadioSecurityWPACipher      INTEGER,
    apRadioSecurityWPAPSKType     INTEGER,
    apRadioSecurityWPAPSK         DisplayString,
    apRadioSecurityWEPKeyType     INTEGER,
    apRadioSecurityWEPEnabled     TruthValue
}

apRadioSecurityIndex OBJECT-TYPE
        SYNTAX      Integer32
        MAX-ACCESS  not-accessible
        STATUS      current
        DESCRIPTION "Radio Index for security settings."
        ::= { apRadioSecurityEntry 1 }

apRadioSecurityWEPAuthType OBJECT-TYPE
	    SYNTAX     INTEGER
               {
                   open(0),
                   shared(1)
               }
        MAX-ACCESS read-write
        STATUS current
        DESCRIPTION
            "This value indicates the type of WEP authentication in use for this radio interface."
        ::= { apRadioSecurityEntry 2 }

apRadioSecuritySharedKeyLen OBJECT-TYPE
	    SYNTAX     INTEGER
               {
				   none(0),
				   sixtyFour(1),
				   oneHundredTwentyEight(2),	
				   oneHundredFiftyTwo(3)	
               }
        MAX-ACCESS read-write
        STATUS current
        DESCRIPTION
            "This value indicates the shared key length for this radio interface."
        ::= { apRadioSecurityEntry 3 }

apRadioSecurityWPAMode OBJECT-TYPE
	    SYNTAX     INTEGER
               {
                   supported(0),
                   required(1),
                   notSupported(2)
               }
        MAX-ACCESS read-write
        STATUS current
        DESCRIPTION
            "This value indicates the state of WPA for this radio interface."
        ::= { apRadioSecurityEntry 4 }

apRadioSecurityWPAKeyType OBJECT-TYPE
	    SYNTAX     INTEGER
               {
                   dot1x(0),
                   presharedkey(1)
               }
        MAX-ACCESS read-write
        STATUS current
        DESCRIPTION
            "This value indicates the type of WPA Key Management in use for this radio interface."
        ::= { apRadioSecurityEntry 5 }

apRadioSecurityWPACipher OBJECT-TYPE
	    SYNTAX     INTEGER
               {
                   wep(0),
                   tkip(1),
                   aes(2)
               }
        MAX-ACCESS read-write
        STATUS current
        DESCRIPTION
            "This value indicates the type of WPA Cipher in use for this radio interface."
        ::= { apRadioSecurityEntry 6 }

apRadioSecurityWPAPSKType OBJECT-TYPE
	    SYNTAX     INTEGER
               {
                   hex(0),
                   alphanumeric(1)
               }
        MAX-ACCESS read-write
        STATUS current
        DESCRIPTION
            "This value indicates the type of WPA Pre Shared Key in use for this radio interface."
        ::= { apRadioSecurityEntry 7 }

apRadioSecurityWPAPSK OBJECT-TYPE
        SYNTAX DisplayString (SIZE(0..80))
        MAX-ACCESS read-write
        STATUS current
        DESCRIPTION
            "This value indicates WPA Pre Shared Key in use for this radio interface."
        ::= { apRadioSecurityEntry 8 }

apRadioSecurityWEPKeyType OBJECT-TYPE
	    SYNTAX     INTEGER
               {
                   hexadecimal(0),
                   alphanumeric(1)
               }
        MAX-ACCESS read-write
        STATUS current
        DESCRIPTION
            "This value indicates the type of WEP Key in use for this radio interface."
        ::= { apRadioSecurityEntry 9 }

apRadioSecurityWEPEnabled OBJECT-TYPE
        SYNTAX TruthValue 
        MAX-ACCESS read-write
        STATUS current
        DESCRIPTION
            "This value indicates whether WEP is enabled."
        ::= { apRadioSecurityEntry 10 }
-- -------------------------------------------------------------
--
apSecuritySsh	        OBJECT IDENTIFIER ::= { apSecurityMgnt 2 }

apSecuritySshServerEnabled OBJECT-TYPE
        SYNTAX TruthValue 
        MAX-ACCESS read-write
        STATUS current
        DESCRIPTION
            "This value indicates whether SSH server is enabled."
        ::= { apSecuritySsh 1 }
        
apSecuritySshServerPort OBJECT-TYPE
        SYNTAX Integer32
        MAX-ACCESS read-write
        STATUS current
        DESCRIPTION
            "This value indicates SSH server's port number."
        DEFVAL      { 22 }
        ::= { apSecuritySsh 2 }

apSecuritySshTelnetServerEnabled OBJECT-TYPE
        SYNTAX TruthValue 
        MAX-ACCESS read-write
        STATUS current
        DESCRIPTION
            "This value indicates whether telnet server is enabled."
        ::= { apSecuritySsh 3 }
        
-- -------------------------------------------------------------
-- - START::apRadioSecurityMgnt TABLE
-- -------------------------------------------------------------


-- -------------------------------------------------------------
-- - START::apRadioInterfaceTable TABLE
-- -------------------------------------------------------------

apRadioInterfaceTable OBJECT-TYPE
        SYNTAX      SEQUENCE OF ApRadioInterfaceEntry
        MAX-ACCESS  not-accessible
        STATUS      current
        DESCRIPTION "Table of descriptive and status information about
                     configuration of each radio."
        ::= { apRadioInterfaceMgnt 1 }

apRadioInterfaceEntry OBJECT-TYPE
        SYNTAX      ApRadioInterfaceEntry
        MAX-ACCESS  not-accessible
        STATUS      current
        DESCRIPTION "An entry in the table, containing information
                     about configuration of one radio of the AP."
        INDEX       { apRadioInterfaceIndex }
        ::= { apRadioInterfaceTable 1 }

ApRadioInterfaceEntry ::= SEQUENCE
{
    apRadioInterfaceIndex          Integer32,
    apRadioInterfaceState          INTEGER,
    apRadioInterfaceAutoChannel    INTEGER,
    apRadioInterfaceTransmitPower  INTEGER,
    apRadioInterfaceClosedSystem   INTEGER,
    apRadioInterfaceMaxAssoc       INTEGER,
    apRadioInterfaceTransmitKey    INTEGER,
    apRadioInterfaceTurboMode      INTEGER,
    apRadioInterfaceDescription    DisplayString,
    apRadioInterfaceDataRate       INTEGER,
    apRadioInterfaceGMode          INTEGER,
    apRadioInterfaceAntennaMode   	INTEGER,
	rogueApState	              	INTEGER,
	rogueApInterval                 INTEGER,
	rogueApDuration                 INTEGER,
	rogueScanNow					INTEGER
}

apRadioInterfaceIndex OBJECT-TYPE
        SYNTAX      Integer32
        MAX-ACCESS  not-accessible
        STATUS      current
        DESCRIPTION "Radio Index for configuration."
        ::= { apRadioInterfaceEntry 1 }

apRadioInterfaceState OBJECT-TYPE
	    SYNTAX     INTEGER
               {
                   enabled(1),
                   disabled(2)
               }
        MAX-ACCESS read-write
        STATUS current
        DESCRIPTION
            "This value indicates the state of the radio interface."
        ::= { apRadioInterfaceEntry 2 }

apRadioInterfaceAutoChannel OBJECT-TYPE
	    SYNTAX     INTEGER
               {
                   enabled(1),
                   disabled(2)
               }
        MAX-ACCESS read-write
        STATUS current
        DESCRIPTION
            "This value indicates whether auto channel selection is enabled or not
			 for this radio interface"
        ::= { apRadioInterfaceEntry 3 }

apRadioInterfaceTransmitPower OBJECT-TYPE
	    SYNTAX     INTEGER
               {
                   min(0),
				   eighth(1),
				   quarter(2),
				   half(3),
				   full(4)
               }
        MAX-ACCESS read-write
        STATUS current
        DESCRIPTION
            "This value indicates the transmit power for this radio interface."
        ::= { apRadioInterfaceEntry 4 }

apRadioInterfaceClosedSystem OBJECT-TYPE
	    SYNTAX     INTEGER
               {
                   enabled(1),
                   disabled(2)
               }
        MAX-ACCESS read-write
        STATUS current
        DESCRIPTION
            "This value indicates whether closed system is enabled for this radio interface."
        ::= { apRadioInterfaceEntry 5 }

apRadioInterfaceMaxAssoc OBJECT-TYPE
        SYNTAX INTEGER (1..64)
        MAX-ACCESS read-write
        STATUS current
        DESCRIPTION
            "This value indicates the max number of clients allowed on this radio interface."
        ::= { apRadioInterfaceEntry 6 }

apRadioInterfaceTransmitKey OBJECT-TYPE
        SYNTAX INTEGER (1..4)
        MAX-ACCESS read-write
        STATUS current
        DESCRIPTION
            "This value indicates default transmit key in use for this radio interface."
        ::= { apRadioInterfaceEntry 7 }

apRadioInterfaceTurboMode OBJECT-TYPE
	    SYNTAX     INTEGER
               {
                   enabled(1),
                   disabled(2)
               }
        MAX-ACCESS read-write
        STATUS current
        DESCRIPTION
            "This value indicates whether turbo mode is enabled for this radio interface."
        ::= { apRadioInterfaceEntry 8 }

apRadioInterfaceDescription OBJECT-TYPE
        SYNTAX DisplayString (SIZE(0..80))
        MAX-ACCESS read-write
        STATUS current
        DESCRIPTION
            "This value indicates the description for this radio interface."
        ::= { apRadioInterfaceEntry 9 }

apRadioInterfaceDataRate OBJECT-TYPE
	    SYNTAX     INTEGER
               {
                   oneMbps(1),
                   twoMbps(2),
                   fiveAndHalfMbps(5), 
                   sixMbps(6), 
                   nineMbps(9), 
                   elevenMbps(11), 
                   twelveMbps(12), 
                   eighteenMbps(18), 
                   twentyFourMbps(24), 
                   thirtySixMbps(36), 
                   fourtyEightMbps(48), 
                   fiftyFourMbps(54),
				   auto(255)
               }
        MAX-ACCESS read-write
        STATUS current
        DESCRIPTION
            "This value indicates the data rate for this radio interface.
			Radio interface A operates at 6, 9, 12, 18, 24, 36, 48, 54.
            Radio interface G operates all listed data rates.   The auto
			setting will attempt to set the best data rate for the interface" 
        ::= { apRadioInterfaceEntry 10 }

apRadioInterfaceGMode OBJECT-TYPE
	    SYNTAX     INTEGER
               {
					bOnly(1),
					gOnly(2),
					bg(3)
               }
        MAX-ACCESS read-write
        STATUS current
        DESCRIPTION
            "This value indicates the radio mode for the 802.11g radio.
			This setting is only valid for the 802.11g interface."
        ::= { apRadioInterfaceEntry 11 }

apRadioInterfaceAntennaMode OBJECT-TYPE
	    SYNTAX     INTEGER
               {
					fixed(1),
					external(2)
               }
        ACCESS read-write
        STATUS mandatory
        DESCRIPTION
            "This value indicates the antenna mode in use for the G-radio. 
			 The values are interpreted as follows:
				fixed(1)	means use both built-in antennas,
				external(2) means use one external antenna on the right side.
			This setting is only valid for the 802.11g interface."
        ::= { apRadioInterfaceEntry 12 }
rogueApState OBJECT-TYPE
	    SYNTAX     INTEGER
               {
                   enabled(1),
                   disabled(2)
               }
        MAX-ACCESS read-write
        STATUS current
        DESCRIPTION
            "This value is used to enable/disable Rogue Ap Detection for 
			this radio interface."
        ::= { apRadioInterfaceEntry 13 }


rogueApInterval OBJECT-TYPE
--	    SYNTAX     INTEGER (60..10080)
	    SYNTAX     INTEGER (30..10080)
        MAX-ACCESS read-write
        STATUS current
        DESCRIPTION
            "How often to scan for Rogue Aps.  The interval in minutes, with default 
			of 720(minutes)." 
        ::= { apRadioInterfaceEntry 14 }

rogueApDuration OBJECT-TYPE
	    SYNTAX     INTEGER (200..1000)
        MAX-ACCESS read-write
        STATUS current
        DESCRIPTION
            "How long to scan each channel (in milliseconds).   A longer duration will yield more 
			complete results. A shorter duration will allow clients a better chance 
			of remaining connected.  Default value is 350(milliseconds)."
        ::= { apRadioInterfaceEntry 15 }

rogueScanNow OBJECT-TYPE
	    SYNTAX     INTEGER
               {
                   enabled(1),
                   disabled(2)
               }
        MAX-ACCESS read-write
        STATUS current
        DESCRIPTION
            "When writing the value to enable, the AP will trigger the Rouge AP scan function.
             The value will always return disable(2)."
        ::= { apRadioInterfaceEntry 16 }
-- -------------------------------------------------------------
-- - END::apRadioInterfaceTable TABLE
-- -------------------------------------------------------------
-- -------------------------------------------------------------
-- START::The apEtherInterfaceMgnt Group
-- -------------------------------------------------------------
--  ==============================
--  apEtherNetConfig Entry
apEtherNetConfig                      
  OBJECT IDENTIFIER ::= { apEtherInterfaceMgnt 1 }


netConfigIPAddress  OBJECT-TYPE
    SYNTAX     IpAddress
    MAX-ACCESS read-write
    STATUS     current
    DESCRIPTION "The IP address of this Net interface.  The default value
		        for this object is 0.0.0.0.  If either the netConfigIPAddress
		        or netConfigSubnetMask are 0.0.0.0, then when the device
		        boots, it may use DHCP to try to figure out what these
		        values should be. If DHCP fails, before the device
		        can talk on the network, this value must be configured
		        (e.g., through a terminal attached to the device)."
    ::= { apEtherNetConfig 1 }

netConfigSubnetMask  OBJECT-TYPE
    SYNTAX     IpAddress
    MAX-ACCESS read-write
    STATUS     current
    DESCRIPTION "The subnet mask of this Net interface.  The default value
		        for this object is 0.0.0.0.  If either the netConfigIPAddress
		        or netConfigSubnetMask are 0.0.0.0, then when the device
		        boots, it may use DHCP to try to figure out what these
		        values should be. If DHCP fails, before the device
		        can talk on the network, this value must be configured
		        (e.g., through a terminal attached to the device)."
    ::= { apEtherNetConfig 2 }

netConfigDefaultGateway  OBJECT-TYPE
    SYNTAX     IpAddress
    MAX-ACCESS read-write
    STATUS     current
    DESCRIPTION "The IP Address of the default gateway.  If this value is
		        undefined or unknown, it shall have the value 0.0.0.0."
    ::= { apEtherNetConfig 3 }

netConfigHttpState OBJECT-TYPE
    SYNTAX     INTEGER
               {
                   enabled(1),
                   disabled(2)
               }
    MAX-ACCESS read-write
    STATUS     current
    DESCRIPTION "Whether HTTP is enabled."
    ::= { apEtherNetConfig 4 }

netConfigHttpPort OBJECT-TYPE
	SYNTAX     INTEGER (514..65535)
    MAX-ACCESS read-write
    STATUS     current
    DESCRIPTION "The port number for HTTP."
    ::= { apEtherNetConfig 5 }

netConfigHttpsState OBJECT-TYPE
    SYNTAX     INTEGER
               {
                   enabled(1),
                   disabled(2)
               }
    MAX-ACCESS read-write
    STATUS     current
    DESCRIPTION "Whether Secure HTTP is enabled."
    ::= { apEtherNetConfig 6 }

netConfigHttpsPort OBJECT-TYPE
	SYNTAX     INTEGER (514..65535)
    MAX-ACCESS read-write
    STATUS     current
    DESCRIPTION "The port number for Secure HTTP."
    ::= { apEtherNetConfig 7 }

netConfigDHCPState OBJECT-TYPE
    SYNTAX     INTEGER
               {
                   enabled(1),
                   disabled(2)
               }
    MAX-ACCESS read-write
    STATUS     current
    DESCRIPTION "Whether DHCP is enabled."
    ::= { apEtherNetConfig 8 }
-- -------------------------------------------------------------
-- END::The apNetConfigMgnt Group
-- -------------------------------------------------------------

-- -------------------------------------------------------------
-- -START::apVLANMgnt - VLAN Mib elements
-- -------------------------------------------------------------

apVLANMgntNativeId OBJECT-TYPE
        SYNTAX INTEGER
        MAX-ACCESS read-write
        STATUS current
        DESCRIPTION
            "This value indicates the native VLAN id."
        ::= { apVLANMgnt 1 }

apVLANMgntState OBJECT-TYPE
	    SYNTAX     INTEGER
               {
                   enabled(1),
                   disabled(2)
               }
        MAX-ACCESS read-only
        STATUS current
        DESCRIPTION
            "This value indicates whether VLANs are enabled or disabled."
        ::= { apVLANMgnt 2 }

apVLANMgntStateNextBoot OBJECT-TYPE
	    SYNTAX     INTEGER
               {
                   enabled(1),
                   disabled(2)
               }
        MAX-ACCESS read-write
        STATUS current
        DESCRIPTION
            "This value indicates the VLANs state for the next reest ."
        ::= { apVLANMgnt 3 }

--apInterfaceVlanId_A OBJECT-TYPE
--        SYNTAX Integer32
--        ACCESS read-write
--        STATUS mandatory
--        DESCRIPTION
--            "This value indicates the native VLAN id of the 802.11 a wireless interface ."
--        ::= { apVLANMgnt 4 }
        
--apInterfaceVlanId_G OBJECT-TYPE
--        SYNTAX Integer32
--        ACCESS read-write
--        STATUS mandatory
--        DESCRIPTION
--            "This value indicates the native VLAN id of the 802.11 g wireless interface ."
--        ::= { apVLANMgnt 5 }
-- -------------------------------------------------------------
apNativeVlanTable OBJECT-TYPE
        SYNTAX      SEQUENCE OF ApNativeVlanEntry
        MAX-ACCESS      not-accessible
        STATUS      current
        DESCRIPTION "Table used to manage the Vlans for each
                     wireless interface."
        ::= { apVLANMgnt 6 }

apNativeVlanEntry OBJECT-TYPE
        SYNTAX      ApNativeVlanEntry
        MAX-ACCESS      not-accessible
        STATUS      current
        DESCRIPTION "An entry in the table, containing information
                     about vlan configuration of one wireless interface."
        INDEX       { apNativeVlanIfIndex, 
		              apNativeVlanSsidNumber }
        ::= { apNativeVlanTable 1 }


ApNativeVlanEntry ::= SEQUENCE
{
    apNativeVlanIfIndex          Integer32,
    apNativeVlanSsidNumber       Integer32,
    apNativeVlanVlanId           Integer32,
    apNativeVlanState            INTEGER
}


apNativeVlanIfIndex OBJECT-TYPE
        SYNTAX      Integer32
        MAX-ACCESS      not-accessible
        STATUS      current
        DESCRIPTION "Interface Index of the wireless interface for which
		             the vlan is assigned to."
        ::= { apNativeVlanEntry 1 }

apNativeVlanSsidNumber OBJECT-TYPE
        SYNTAX      Integer32
        MAX-ACCESS      not-accessible
        STATUS      current
        DESCRIPTION "Associated Number for Service Set Id (SSID) of the 
		             wireless interface for which the vlan is assigned to.  
					 Note: This is for future support of multiple SSIDs 
					 per radio interface."
        ::= { apNativeVlanEntry 2 }

apNativeVlanVlanId OBJECT-TYPE
        SYNTAX Integer32
        MAX-ACCESS read-write
        STATUS current
        DESCRIPTION
            "This value indicates the native VLAN id of the wireless interface associated
			  with the if index and the SSID number(if it is not 0)."
        ::= { apNativeVlanEntry 3 }

apNativeVlanState OBJECT-TYPE
	    SYNTAX     INTEGER
               {
                   enabled(1),
                   disabled(2)
               }
        MAX-ACCESS read-write
        STATUS current
        DESCRIPTION
            "This value indicates the Native VLANs state."
        ::= { apNativeVlanEntry 4 }
-- -------------------------------------------------------------
-- -END::apVLANMgnt - VLAN Mib elements
-- -------------------------------------------------------------
-- -------------------------------------------------------------
-- START::The apAuthenticationMgnt Group
-- -------------------------------------------------------------
--  ==============================
--  dot11AuthenticationEntry TABLE
apAuthenticationSetupEntry                      
  OBJECT IDENTIFIER ::= { apAuthenticationMgnt 1 }

ap8021xState OBJECT-TYPE
	    SYNTAX     INTEGER
               {
                   disabled(0),
                   supported(1),
                   required(2)
               }
        MAX-ACCESS read-write
        STATUS current
        DESCRIPTION
            "This attribute indicates that the Enterprise the state
            of the 802.1x authentication algorithm."

    ::= { apAuthenticationSetupEntry 1 }

ap8021xBroadcastKeyRefreshRate OBJECT-TYPE
        SYNTAX INTEGER (0..1440)
        MAX-ACCESS read-write
        STATUS current
        DESCRIPTION
            "The number (in minutes) between changing the broadcast key for 
			802.1x and WPA clients"

    ::= { apAuthenticationSetupEntry 2 }

ap8021xSessionKeyRefreshRate OBJECT-TYPE
        SYNTAX INTEGER (0..1440)
        MAX-ACCESS read-write
        STATUS current
        DESCRIPTION
            "The number (in minutes) between changing session keys for 
			802.1x and WPA clients"

    ::= { apAuthenticationSetupEntry 3 }

ap8021xReauthenticationTimeout OBJECT-TYPE
        SYNTAX INTEGER (0..1440)
        MAX-ACCESS read-write
        STATUS current
        DESCRIPTION
            "The number (in minutes) between forcing 802.1x clients to 
			reauthenticate"

    ::= { apAuthenticationSetupEntry 4 }

apAuthenticationMode OBJECT-TYPE
	    SYNTAX     INTEGER
               {
                   disabled(0),
                   local(1),
                   radius(2)
               }
        ACCESS read-write
        STATUS mandatory
        DESCRIPTION
            "This value indicates the type of mac authentication or RADUIS authentication in use,
             or not in use."
	    ::= { apAuthenticationSetupEntry 5 }

--  ==============================
--  apAuthenticationServerTable
apAuthenticationServerTable OBJECT-TYPE
        SYNTAX      SEQUENCE OF ApAuthenticationServerEntry
        MAX-ACCESS  not-accessible
        STATUS      current
        DESCRIPTION "Table of descriptive and status information about
                     configuration of each authentication server."
        ::= { apAuthenticationMgnt 2 }

apAuthenticationServerEntry OBJECT-TYPE
        SYNTAX      ApAuthenticationServerEntry
        MAX-ACCESS  not-accessible
        STATUS      current
        DESCRIPTION "An entry in the table, containing information
                     about configuration of one authentication server of the AP."
        INDEX       { apAuthenticationServerIndex }
        ::= { apAuthenticationServerTable 1 }

ApAuthenticationServerEntry ::= SEQUENCE
{
    apAuthenticationServerIndex        Integer32,
    apAuthenticationServer             IpAddress,
    apAuthenticationPort               INTEGER,
    apAuthenticationKey                DisplayString,
    apAuthenticationRetransmit         INTEGER,
    apAuthenticationTimeout            INTEGER,
    apAuthenticationAcctPort		   INTEGER,
    apAuthenticationAcctInterimUpdate   INTEGER
}

apAuthenticationServerIndex OBJECT-TYPE
        SYNTAX      Integer32
        MAX-ACCESS  not-accessible
        STATUS      current
        DESCRIPTION "Index of the Authentication Server"
        ::= { apAuthenticationServerEntry 1 }


apAuthenticationServer OBJECT-TYPE
        SYNTAX IpAddress
        MAX-ACCESS read-write
        STATUS current
        DESCRIPTION
            "This value indicates the IP address of the authentication server."

    ::= { apAuthenticationServerEntry 2 }

apAuthenticationPort OBJECT-TYPE
        SYNTAX INTEGER (1024..65535)
        MAX-ACCESS read-write
        STATUS current
        DESCRIPTION
            "This value indicates the UDP Port used by the authentication server."

    ::= { apAuthenticationServerEntry 3 }

apAuthenticationKey OBJECT-TYPE
        SYNTAX DisplayString (SIZE(0..20))
        MAX-ACCESS read-write
        STATUS current
        DESCRIPTION
            "This value indicates the shared key used by the authentication server."

    ::= { apAuthenticationServerEntry 4 }

apAuthenticationRetransmit OBJECT-TYPE
        SYNTAX INTEGER (1..30)
        MAX-ACCESS read-write
        STATUS current
        DESCRIPTION
            "This value indicates the retransmit timer length used by the 
            authentication server."

    ::= { apAuthenticationServerEntry 5 }

apAuthenticationTimeout OBJECT-TYPE
        SYNTAX INTEGER (1..60)
        MAX-ACCESS read-write
        STATUS current
        DESCRIPTION
            "This value indicates the Timeout value(sec) used by the 
			authentication server."

    ::= { apAuthenticationServerEntry 6 }

apAuthenticationAcctPort OBJECT-TYPE
        SYNTAX      INTEGER(0..65535) 
        MAX-ACCESS  read-write
        STATUS      current
        DESCRIPTION "UDP Accounting Port.  The valid range is from
		1024-65535.  A value of 0 means accounting is disabled."
        ::= { apAuthenticationServerEntry 7 }

apAuthenticationAcctInterimUpdate OBJECT-TYPE
        SYNTAX      INTEGER(60..86400) 
        MAX-ACCESS  read-write
        STATUS      current
        DESCRIPTION "The interval between sending accounting
		updates."
        ::= { apAuthenticationServerEntry 8 }
--  ==============================
--  apAuthenticationSupplicantTable TABLE
apAuthenticationSupplicantTable OBJECT-TYPE
        SYNTAX      SEQUENCE OF ApAuthenticationSupplicantEntry
        MAX-ACCESS  not-accessible
        STATUS      current
        DESCRIPTION "Table of descriptive and status information about
                     configuration of supplicant"
        ::= { apAuthenticationMgnt 3 }


apAuthenticationSupplicantEntry OBJECT-TYPE
        SYNTAX      ApAuthenticationSupplicantEntry
        MAX-ACCESS  not-accessible
        STATUS      current
        DESCRIPTION "An entry in the table, containing information
                     about configuration of one supplicant."
        INDEX       { ap8021xSuppIndex }
        ::= { apAuthenticationSupplicantTable 1 }


ApAuthenticationSupplicantEntry ::= SEQUENCE
{
    ap8021xSuppIndex          Integer32,
    ap8021xSuppState          INTEGER,
    ap8021xSuppUser           DisplayString,
    ap8021xSuppPasswd         DisplayString
}

ap8021xSuppIndex OBJECT-TYPE
        SYNTAX      Integer32
        MAX-ACCESS  not-accessible
        STATUS      current
        DESCRIPTION "Index of the interface for which this supplicant is
		             running.  Currently only the ethernet interface."
        ::= { apAuthenticationSupplicantEntry 1 }


ap8021xSuppState OBJECT-TYPE
	    SYNTAX     INTEGER
               {
                   disabled(0),
                   enabled(1)
               }
        MAX-ACCESS read-write
        STATUS current
        DESCRIPTION
            "This object is used to enable or disable the 802.1x supplicant."

    ::= { apAuthenticationSupplicantEntry 2 }

ap8021xSuppUser OBJECT-TYPE
        SYNTAX DisplayString (SIZE(1..32))
        MAX-ACCESS read-write
        STATUS current
        DESCRIPTION
            "This value indicates the username for supplicant. If value is
			 configured, will display ****.  Else will display EMPTY."
        ::= { apAuthenticationSupplicantEntry 3 }
		
ap8021xSuppPasswd OBJECT-TYPE
        SYNTAX DisplayString (SIZE(1..32))
        MAX-ACCESS read-write
        STATUS current
        DESCRIPTION
            "This value indicates the password for supplicant. If value is
			 configured, will display ****.  Else will display EMPTY."
        ::= { apAuthenticationSupplicantEntry 4 }
-- -------------------------------------------------------------
-- END::The apAuthenticationMgnt Group
-- -------------------------------------------------------------

-- -------------------------------------------------------------
-- START::The apWStationSessionMgnt Group
-- -------------------------------------------------------------	

apWStationSessionTable OBJECT-TYPE
	SYNTAX		SEQUENCE OF ApWStationSessionEntry
	MAX-ACCESS	not-accessible
	STATUS		current
	DESCRIPTION
		"This table list all sessions (wireless stations) status"
	::= { apWStationSessionMgnt 1 }
	
apWStationSessionEntry OBJECT-TYPE
	SYNTAX		ApWStationSessionEntry
	MAX-ACCESS	not-accessible
	STATUS		current
	DESCRIPTION
		"An entry in the table, containing information
		about status and statistics of the wireless station."
    INDEX { apWStationSessionIfIndex, apWStationSessionStationAddres } 
	::= { apWStationSessionTable 1 }

ApWStationSessionEntry ::= SEQUENCE 
{
	apWStationSessionIfIndex				Integer32,
	apWStationSessionStationAddres 			MacAddress,
	apWStationSessionAuthenticated			TruthValue,
	apWStationSessionAssociated				TruthValue,
	apWStationSessionIsForwarding			TruthValue,
	apWStationSessionKeyType				INTEGER,
	apWStationSessionAssociationId			Integer32,
	apWStationSessionLastAuthenticatedTime	TimeTicks,
	apWStationSessionAssociatedTime			TimeTicks,
	apWStationSessionLastAssociatedTime 	TimeTicks,
	apWStationSessionLastDisassociatedTime	TimeTicks,
	apWStationSessionTxPacketCount			Counter32,
	apWStationSessionRxPacketCount			Counter32,
	apWStationSessionTxByteCount			Counter32,
	apWStationSessionRxByteCount			Counter32,
	apWStationSessionVlanID					INTEGER
}

apWStationSessionIfIndex OBJECT-TYPE
    SYNTAX      Integer32
    MAX-ACCESS	not-accessible
    STATUS      current
    DESCRIPTION 
    	"Interface index for the radio this session is associated
		 with."
    ::= { apWStationSessionEntry 1 }
        
apWStationSessionStationAddres OBJECT-TYPE 
    SYNTAX		MacAddress 
    MAX-ACCESS	not-accessible 
    STATUS		current 
    DESCRIPTION 
    	"The unique MAC Address of the station for this session." 
    ::= { apWStationSessionEntry 2 }

apWStationSessionAuthenticated OBJECT-TYPE
	SYNTAX TruthValue
	MAX-ACCESS	read-only
	STATUS		current
	DESCRIPTION
		"Whether the session is authenticated or not."
	::= { apWStationSessionEntry 3 }

apWStationSessionAssociated OBJECT-TYPE
	SYNTAX TruthValue
	MAX-ACCESS	read-only
	STATUS		current
	DESCRIPTION
		"Whether the session is associated or not. It is rare case that 
		not associated stations show up in the table."
	::= { apWStationSessionEntry 4 }
	
apWStationSessionIsForwarding OBJECT-TYPE
	SYNTAX TruthValue
	MAX-ACCESS	read-only
	STATUS		current
	DESCRIPTION
		"Whether the AP is forwarding the client station traffic (higher level authentication)"
	::= { apWStationSessionEntry 5 }
	
apWStationSessionKeyType OBJECT-TYPE
	SYNTAX INTEGER
	{
		none(1),
		staticWep(2),
		dynamicWep(3),
		wpaWep(4),
		wpaTkip(5),
		wpaAes(6)
	}	
	MAX-ACCESS	read-only
	STATUS		current
	DESCRIPTION
		"The encryption key type used by the station. Note that wpa-wep is not supported"
	::= { apWStationSessionEntry 6 }
	
apWStationSessionAssociationId OBJECT-TYPE
	SYNTAX Integer32
	MAX-ACCESS	read-only
	STATUS		current
	DESCRIPTION
		"The internal association identify number"
	::= { apWStationSessionEntry 7 }

apWStationSessionLastAuthenticatedTime OBJECT-TYPE
	SYNTAX		TimeTicks
	MAX-ACCESS	read-only
	STATUS		current
	DESCRIPTION
		"This is the time in hundredths of a second last time the client
		is authenticated. Note that a session may be authenticated multiple times. 
		The value is related to the system startup"
	::= { apWStationSessionEntry 8 }

apWStationSessionAssociatedTime OBJECT-TYPE
	SYNTAX		TimeTicks
	MAX-ACCESS	read-only
	STATUS		current
	DESCRIPTION
		"This is the time in hundredths of a second since the client 
		associated. The value is related to the system startup"
	::= { apWStationSessionEntry 9 }
	
apWStationSessionLastAssociatedTime OBJECT-TYPE
	SYNTAX		TimeTicks
	MAX-ACCESS	read-only
	STATUS		current
	DESCRIPTION
		"This is the time in hundredths of a second when the client 
		associated in last session. The value is related to the system startup"
	::= { apWStationSessionEntry 10 }
	
apWStationSessionLastDisassociatedTime OBJECT-TYPE
	SYNTAX		TimeTicks
	MAX-ACCESS	read-only
	STATUS		current
	DESCRIPTION
		"This is the time in hundredths of a second when the client 
		disassociated in last session. The value is related to the system startup"
	::= { apWStationSessionEntry 11 }

apWStationSessionTxPacketCount OBJECT-TYPE
	SYNTAX	Counter32
	MAX-ACCESS	read-only
	STATUS	current
	DESCRIPTION
		"This is the number of packets transmitted"
	::= { apWStationSessionEntry 12 }

apWStationSessionRxPacketCount OBJECT-TYPE
	SYNTAX	Counter32
	MAX-ACCESS	read-only
	STATUS	current
	DESCRIPTION
		"This is the number of packets received"
	::= { apWStationSessionEntry 13 }

apWStationSessionTxByteCount OBJECT-TYPE
	SYNTAX	Counter32
	MAX-ACCESS	read-only
	STATUS	current
	DESCRIPTION
		"This is the number of bytes transmitted"
	::= { apWStationSessionEntry 14 }

apWStationSessionRxByteCount OBJECT-TYPE
	SYNTAX	Counter32
	MAX-ACCESS	read-only
	STATUS	current
	DESCRIPTION
		"This is the number of bytes received"
	::= { apWStationSessionEntry 15 }

apWStationSessionVlanID OBJECT-TYPE
	SYNTAX INTEGER
	MAX-ACCESS	read-only
	STATUS		current
	DESCRIPTION
		"The current Vlan Id used by the station."
	::= { apWStationSessionEntry 16 }
	

-- -------------------------------------------------------------
-- End::The apStationSession Group
-- -------------------------------------------------------------

-- -------------------------------------------------------------
-- START::The apRogueApMgnt Group
-- -------------------------------------------------------------

rogueApDetectionTable OBJECT-TYPE
        SYNTAX      SEQUENCE OF RogueApEntry
        MAX-ACCESS  not-accessible
        STATUS      current
        DESCRIPTION "Table of each AP that has been detected."
        ::= { apRogueApMgnt 1 }

rogueApEntry OBJECT-TYPE
        SYNTAX      RogueApEntry
        MAX-ACCESS  not-accessible
        STATUS      current
        DESCRIPTION "An entry in the table, containing information
                     about any AP detected."
        INDEX       { rogueApIndex }
        ::= { rogueApDetectionTable 1 }

RogueApEntry ::= SEQUENCE
{
    rogueApIndex             INTEGER,
    rogueApBssid             DisplayString,
    rogueApSsid              DisplayString,
    rogueApPortNumber        Integer32,
	rogueApChannelNumber     Integer32,
	rogueApRSSIValue         Integer32
}

rogueApIndex OBJECT-TYPE
        SYNTAX      INTEGER (1..128)
        MAX-ACCESS  not-accessible
        STATUS      current
        DESCRIPTION "Monotonically increasing index."
        ::= { rogueApEntry 1 }

rogueApBssid OBJECT-TYPE
        SYNTAX     DisplayString (SIZE(0..6))
        MAX-ACCESS read-only
        STATUS current
        DESCRIPTION
            "The AP BSSID"
        ::= { rogueApEntry 2 } 

rogueApSsid OBJECT-TYPE
        SYNTAX     DisplayString (SIZE(0..40))
        MAX-ACCESS read-only
        STATUS current
        DESCRIPTION
            "The AP SSID"
        ::= { rogueApEntry 3 } 

rogueApPortNumber OBJECT-TYPE
    SYNTAX      Integer32
    MAX-ACCESS	read-only
    STATUS      current
    DESCRIPTION 
    	"Interface index for the radio."
    ::= { rogueApEntry 4 }

rogueApChannelNumber OBJECT-TYPE
    SYNTAX      Integer32
    MAX-ACCESS	read-only
    STATUS      current
    DESCRIPTION 
    	"Channel where Ap detected."
    ::= { rogueApEntry 5 }

rogueApRSSIValue OBJECT-TYPE
    SYNTAX      Integer32
    MAX-ACCESS	read-only
    STATUS      current
    DESCRIPTION 
    	"RSSI for AP detected."
    ::= { rogueApEntry 6 }
-- -------------------------------------------------------------
--
apRougeApControl	        OBJECT IDENTIFIER ::= { apRogueApMgnt 2 }

rogueApRADIUSAuthenticate OBJECT-TYPE
	    SYNTAX     INTEGER
               {
                   enabled(1),
                   disabled(2)
               }
        MAX-ACCESS read-write
        STATUS current
        DESCRIPTION
            "Value is used to enable/disable RADIUS Authentication. "
        ::= { apRougeApControl 1 }

-- -------------------------------------------------------------
-- END::The apRogueApMgnt Group
-- -------------------------------------------------------------
-- -------------------------------------------------------------
-- START::The apAdminMgnt Group
-- -------------------------------------------------------------
apAdminUsername OBJECT-TYPE
        SYNTAX DisplayString (SIZE(0..16))
        MAX-ACCESS read-write
        STATUS current
        DESCRIPTION
            "This value indicates the username for management login."
        ::= { apAdminMgnt 1 }

appAdminPassword OBJECT-TYPE
        SYNTAX DisplayString (SIZE(0..16))
        MAX-ACCESS read-write
        STATUS current
        DESCRIPTION
            "This value indicates the password for management login."
        ::= { apAdminMgnt 2 }
-- -------------------------------------------------------------
-- End::The apAdminMgnt Group
-- -------------------------------------------------------------
-- -------------------------------------------------------------
-- START::The apResetMgt Group
-- -------------------------------------------------------------
apRestartOpCodeFile OBJECT-TYPE
        SYNTAX      DisplayString (SIZE(0..127))
        MAX-ACCESS  read-write
        STATUS      current
        DESCRIPTION "Name of op-code file for start-up."
        ::= { apResetMgt 1 }

apRestartControl  OBJECT-TYPE
	    SYNTAX     INTEGER {
			running(1),
        	warmBoot(2),
            coldBoot(3)
        }
	    MAX-ACCESS read-write
	    STATUS     current
	    DESCRIPTION "Setting this object to warmBoot(2) causes the device to
			        restart the application software with current configuration
			        parameters saved in non-volatile memory.  Setting this
			        object to coldBoot(3) causes the device to reinitialize
			        configuration parameters in non-volatile memory to default
			        values and restart the application software.  When the device
			        is running normally, this variable has a value of running(1)."
		::= { apResetMgt 2 }
-- -------------------------------------------------------------
-- End::The apResetMgt Group
-- -------------------------------------------------------------

-- -------------------------------------------------------------
-- START::The apSNTPMgnt Group
-- -------------------------------------------------------------
apSNTPState OBJECT-TYPE
	    SYNTAX     INTEGER
               {
                   enabled(1),
                   disabled(2)
               }
        MAX-ACCESS read-write
        STATUS current
        DESCRIPTION
            "This value indicates whether SNTP is enabled or not. At least one of the 
			 SNTP servers must have a valid IP address before SNTP can be enabled."
        ::= { apSNTPMgnt 1 }

apSNTPPrimaryServer OBJECT-TYPE
        SYNTAX IpAddress
        MAX-ACCESS read-write
        STATUS current
        DESCRIPTION
            "This value indicates the IP address of the primary SNTP server."
        ::= { apSNTPMgnt 2 }

apSNTPSecondaryServer OBJECT-TYPE
        SYNTAX IpAddress
        MAX-ACCESS read-write
        STATUS current
        DESCRIPTION
            "This value indicates the IP address of the secondary SNTP server."
        ::= { apSNTPMgnt 3 }

apSNTPTimezone OBJECT-TYPE
	    SYNTAX     INTEGER
               {
					enewetakKwajalein(0),
					midwayIsland(1),
					hawaii(2),
					alaska(3),
					pacific(4),
					arizona(5),
					mountain(6),
					central(7),
					mexicoCity(8),
					saskatchewan(9),
					bogota(10),
					eastern(11),
					indiana(12),
					atlantic(13),
					caracas(14),
					santiago(15),
					newfoundland(16),
					brasilia(17),
					buenos(18),
					midAtlantic(19),
					azores(20),
					casablanca(21),
					greenwichMeanTimeDublin(22),
					greenwichMeanTimeLisbon(23),
					amsterdam(24),
					stockhoim(25),
					bratislava(26),
					prague(27),
					paris(28),
					sofija(29),
					athens(30),
					bucharest(31),
					cairo(32),
					harare(33),
					helsinki(34),
					israel(35),
					baghdad(36),
					moscow(37),
					tehran(38),
					abuDhabi(39),
					vogograd(40),
					islamabad(41),
					almaty(42),
					bangkok(43),
					beijing(44),
					taipei(45),
					tokyo(46),
					brisbane(47),
					canberra(48),
					guam(49),
					hobart(50),
					magadan(51),
					fiji(52),
					wellington(53)
               }
        MAX-ACCESS read-write
        STATUS current
        DESCRIPTION
            "This value indicates which timezone to use."
        ::= { apSNTPMgnt 4 }

apSNTPDST OBJECT-TYPE
	    SYNTAX     INTEGER
               {
                   enabled(1),
                   disabled(2)
               }
        MAX-ACCESS read-write
        STATUS current
        DESCRIPTION
            "This value indicates whether Daylight Savings Time is enabled or not."
        ::= { apSNTPMgnt 5 }

apSNTPDSTStartMonth OBJECT-TYPE
        SYNTAX INTEGER (1..12)
        MAX-ACCESS read-write
        STATUS current
        DESCRIPTION
            "This value indicates the starting month for Daylight Savings Time."
        ::= { apSNTPMgnt 6 }

apSNTPDSTStartDay OBJECT-TYPE
        SYNTAX INTEGER (1..31)
        MAX-ACCESS read-write
        STATUS current
        DESCRIPTION
            "This value indicates the starting day for Daylight Savings Time."
        ::= { apSNTPMgnt 7 }

apSNTPDSTEndMonth OBJECT-TYPE
        SYNTAX INTEGER (1..12)
        MAX-ACCESS read-write
        STATUS current
        DESCRIPTION
            "This value indicates the ending month for Daylight Savings Time."
        ::= { apSNTPMgnt 8 }

apSNTPDSTEndDay OBJECT-TYPE
        SYNTAX INTEGER (1..31)
        MAX-ACCESS read-write
        STATUS current
        DESCRIPTION
            "This value indicates the ending day for Daylight Savings Time."
        ::= { apSNTPMgnt 9 }

-- -------------------------------------------------------------
-- End::The apSNTPMgnt Group
-- -------------------------------------------------------------

-- -------------------------------------------------------------
-- START::The apDNSMgnt Group
-- -------------------------------------------------------------
apDNSPrimaryServer OBJECT-TYPE
        SYNTAX IpAddress
        MAX-ACCESS read-write
        STATUS current
        DESCRIPTION
            "This value indicates the IP address of the primary DNS server."
        ::= { apDNSMgnt 1 }

apDNSSecondaryServer OBJECT-TYPE
        SYNTAX IpAddress
        MAX-ACCESS read-write
        STATUS current
        DESCRIPTION
            "This value indicates the IP address of the secondary DNS server."
        ::= { apDNSMgnt 2 }
-- -------------------------------------------------------------
-- End::The apDNSMgnt Group
-- -------------------------------------------------------------

-- -------------------------------------------------------------
-- START::The apIappMgnt Group
-- -------------------------------------------------------------
apIappEnabled OBJECT-TYPE
        SYNTAX      INTEGER
                    {
                        enabled(1),
                        disabled(2)
                    }
        MAX-ACCESS read-write
        STATUS current
        DESCRIPTION
            "Whether IAPP is enabled."
        ::= { apIappMgnt 1 }
-- -------------------------------------------------------------
-- End::The apIappMgnt Group
-- -------------------------------------------------------------
-- -------------------------------------------------------------
-- START::The apSyslogConfigMgnt Group
-- --------------------------------------------------------------
apLogConfigState OBJECT-TYPE
	    SYNTAX     INTEGER
               {
                   enabled(1),
                   disabled(2)
               }
        MAX-ACCESS read-write
        STATUS current
        DESCRIPTION "This value indicates whether syslog is enabled."
        ::= { apSyslogConfigMgnt 1 }

apSyslogConsoleState OBJECT-TYPE
	    SYNTAX     INTEGER
               {
                   enabled(1),
                   disabled(2)
               }
        MAX-ACCESS read-write
        STATUS current
        DESCRIPTION "This value indicates whether syslog console logging is enabled."
        ::= { apSyslogConfigMgnt 2 }

apSyslogLevel OBJECT-TYPE
        SYNTAX INTEGER
               {
                   emergency(0),
                   alert(1),
                   critical(2),
                   error(3),
                   warning(4),
                   notice(5),
                   info(6),
                   debug(7)
               }
        MAX-ACCESS read-write
        STATUS current
        DESCRIPTION "This value indicates the syslog logging level."
        ::= { apSyslogConfigMgnt 3 }
-- -------------------------------------------------------------
-- START::The apSyslogServerTable         
apSyslogServerTable OBJECT-TYPE
        SYNTAX      SEQUENCE OF ApSyslogServerEntry
        MAX-ACCESS  not-accessible
        STATUS      current
        DESCRIPTION "Table of descriptive and status information about
                     configuration of each syslog server."
        ::= { apSyslogConfigMgnt 4 }

apSyslogServerEntry OBJECT-TYPE
        SYNTAX      ApSyslogServerEntry
        MAX-ACCESS  not-accessible
        STATUS      current
        DESCRIPTION "An entry in the table, containing information
                     about configuration of one syslog server of the AP."
        INDEX       { apSyslogServerIndex }
        ::= { apSyslogServerTable 1 }

ApSyslogServerEntry ::= SEQUENCE
{
    apSyslogServerIndex        Integer32,
    apSyslogServerState        INTEGER,
    apSyslogServerIPAddress    IpAddress,
    apSyslogServerPort         INTEGER
}

apSyslogServerIndex OBJECT-TYPE
        SYNTAX      Integer32
        MAX-ACCESS  not-accessible
        STATUS      current
        DESCRIPTION "Index of the Syslog Server"
        ::= { apSyslogServerEntry 1 }


apSyslogServerState OBJECT-TYPE
	    SYNTAX     INTEGER
               {
                   enabled(1),
                   disabled(2)
               }
        MAX-ACCESS read-write
        STATUS current
        DESCRIPTION
            "This value indicates whether the syslog server is enabled."
    ::= { apSyslogServerEntry 2 }

apSyslogServerIPAddress OBJECT-TYPE
        SYNTAX IpAddress
        MAX-ACCESS read-write
        STATUS current
        DESCRIPTION
            "This value indicates the IP address of the syslog server."
    ::= { apSyslogServerEntry 3 }

apSyslogServerPort OBJECT-TYPE
        SYNTAX INTEGER (1024..65535)
        MAX-ACCESS read-write
        STATUS current
        DESCRIPTION
            "This value indicates the UDP Port used by the syslog server."
    ::= { apSyslogServerEntry 4 }
-- END::The apSyslogServerTable 
-- -------------------------------------------------------------
-- End::The apSyslogConfigMgnt Group
-- -------------------------------------------------------------
-- -------------------------------------------------------------
-- START::The apEventLogMgnt Group
-- -------------------------------------------------------------
apEventLogTable OBJECT-TYPE
	SYNTAX		SEQUENCE OF ApEventLogEntry
	MAX-ACCESS	not-accessible
	STATUS		current
	DESCRIPTION
		"This table is a snapshot of the current event log."
	::= { apEventLogMgnt 1 }
	
apEventLogEntry OBJECT-TYPE
	SYNTAX		ApEventLogEntry
	MAX-ACCESS	not-accessible
	STATUS		current
	DESCRIPTION
		"An entry in the table, containing one message
		 from the event log."
    INDEX { apEventLogIndex } 
	::= { apEventLogTable 1 }

ApEventLogEntry ::= SEQUENCE 
{
	apEventLogIndex		INTEGER,
	apEventLogMessage    DisplayString
}

apEventLogIndex OBJECT-TYPE
        SYNTAX      INTEGER (1..128) 
        MAX-ACCESS  not-accessible
        STATUS      current
        DESCRIPTION "Index of the Event Log Message"
        ::= { apEventLogEntry 1 }

apEventLogMessage OBJECT-TYPE
        SYNTAX     DisplayString (SIZE(0..256))
        MAX-ACCESS read-only
        STATUS current
        DESCRIPTION
            "The Event Log Message"
        ::= { apEventLogEntry 2 }  

apEventLogClear OBJECT-TYPE
	SYNTAX INTEGER
               {
                   clearLog(1)
               }
        MAX-ACCESS read-write
        STATUS current
        DESCRIPTION
            "This object is set to 1 to clear the event log.  When read, the value
             will have no meaning."
        ::= { apEventLogMgnt 2 }

-- -------------------------------------------------------------
-- End::The apEventLogMgnt Group
-- -------------------------------------------------------------
-- -------------------------------------------------------------
-- -START:: apNotificationTrapTreebjects
-- -------------------------------------------------------------
apNotificationObjects  OBJECT IDENTIFIER ::= { apNotificationTrapTree 1 }

apNotificationDot11MacAddr OBJECT-TYPE
        SYNTAX MacAddress
        MAX-ACCESS not-accessible
        STATUS current
        DESCRIPTION
            "Mac Address of the affected interface, returned with traps only." 
        ::= { apNotificationObjects 1 }

apNotificationDot11Station OBJECT-TYPE
		SYNTAX MacAddress
		MAX-ACCESS not-accessible
		STATUS current
		DESCRIPTION
			"This attribute holds the MAC address of the wireless station"
	::= { apNotificationObjects 2 }

apNotificationDot11RequestType OBJECT-TYPE
		SYNTAX INTEGER
		{
		unknown(1),
		association(2),
		reAssociation(3),
		authentication(4)
		}
		MAX-ACCESS not-accessible
		STATUS current
		DESCRIPTION
			"This attribute defines the request type sent by the station.
                Value = 1: Unknown request type
                Value = 2: Association Request
                Value = 3: Re-association Request
		Value = 4: Authentication"
	::= { apNotificationObjects 3 }

apNotificationDot11ReasonCode OBJECT-TYPE
		SYNTAX INTEGER
		{
		invalidModeOrState(1),
		unAuthenticatedStation(2),
		internalError(3),
		outOfSequenceFrame(4),
		unsupportedAlgorithm(5),
		invalidFrameLngth(6),
		wepRequiredOnAP(7),
		wepNotAllowed(8),
		challengeTextMismatch(9)
		}
		MAX-ACCESS not-accessible
		STATUS current
		DESCRIPTION
			"This attribute defines the reason for the failure of an operation.
                Value = 1: Invalid mode/state
                Value = 2: Station not authenticated.
				Value = 3: Internal error
				Value = 4: Out of sequence frame
				Value = 5: Un-supportd algorithm
				Value = 6: Invalid frame length
				Value = 7: WEP is required on the AP
				Value = 8: WEP not allowed
				Value = 9: Challenge text mismatch"
	::= { apNotificationObjects 4 }

apNotificationDot11IpAddress OBJECT-TYPE
        SYNTAX IpAddress
        MAX-ACCESS not-accessible
        STATUS current
        DESCRIPTION
            "This value indicates the IP address of the Access Point"
        ::= { apNotificationObjects 5 }

apNotificationDot11AuthenticatorMacAddr OBJECT-TYPE
		SYNTAX MacAddress
		MAX-ACCESS not-accessible
		STATUS current
		DESCRIPTION
			"This attribute holds the MAC address of the authenticator for the AP."
	::= { apNotificationObjects 6 }



apNotificationTrapObjects  OBJECT IDENTIFIER ::= { apNotificationTrapTree 2 }

sysSystemUp NOTIFICATION-TYPE
--        OBJECTS { }
        STATUS current
        DESCRIPTION
        
		"The system up notification shall be sent when the AP 
		is fully up and running."

    ::= { apNotificationTrapObjects 1 }

sysSystemDown NOTIFICATION-TYPE
--        OBJECTS { }
        STATUS current
        DESCRIPTION
        
		"The system down notification shall be sent before the AP 
		is about to reboot."

    ::= { apNotificationTrapObjects 2 }

sysRadiusServerChanged NOTIFICATION-TYPE
--        OBJECTS { }
        STATUS current
        DESCRIPTION
        
		"The RADIUS server changed notification shall be sent when
		 the RADIUS server has changed from Primary / Secondary to 
		 Secondary / Primary."

    ::= { apNotificationTrapObjects 3 }

dot11StationAssociation NOTIFICATION-TYPE
        OBJECTS { apNotificationDot11Station }
        STATUS current
        DESCRIPTION
        
		"The associate notification shall be sent when a station successfully 
		associates with the Access Point. The value of the notification shall 
		include the MAC address of the station that has associated."

    ::= { apNotificationTrapObjects 4 }

dot11StationReAssociation NOTIFICATION-TYPE
        OBJECTS { apNotificationDot11Station }
        STATUS current
        DESCRIPTION
        
		"The re-associate notification shall be sent when a station 
		successfully re-associates with the Access Point. The value of the 
		notification shall include the MAC address of the station 
		that has associated."

    ::= { apNotificationTrapObjects 5 }

dot11StationAuthentication NOTIFICATION-TYPE
        OBJECTS { apNotificationDot11Station }
        STATUS current
        DESCRIPTION
        
		"The authentication notification shall be sent when a station 
		successfully authenticates with the Access Point. The value of the 
		notification shall include the MAC address of the station 
		that has authenticated."

    ::= { apNotificationTrapObjects 6 }

-- Note that the following is different from the standard 802.11 mib dot11AuthenticateFail Notification
-- This one also has a reason code within the trap.

dot11StationRequestFail NOTIFICATION-TYPE
        OBJECTS { apNotificationDot11Station, apNotificationDot11RequestType, apNotificationDot11ReasonCode }
        STATUS current
        DESCRIPTION
        
		"The station request fail shall be sent out when a station 
		fails to associate / re-associate / authenticate with the 
		Access Point. The notification shall include the MAC address 
		of the station and the reason code for the failure."

    ::= { apNotificationTrapObjects 7 }


-- dot11InterfaceAGFail NOTIFICATION-TYPE
--        OBJECTS { }
--        STATUS current
--        DESCRIPTION
--        
--		"The InterfaceAGFail notification shall be sent out when 
--		802.11a/802.11g wireless interface has failed."
--
--    ::= { apNotificationTrapObjects 8 }

dot1xMacAddrAuthSuccess NOTIFICATION-TYPE
        OBJECTS { apNotificationDot11Station }
        STATUS current
        DESCRIPTION
        
		"The 802.1x MAC address authentication success notification shall 
		be sent when a station successfully authenticates the MAC address
		with the RADIUS server. The value of the notification shall 
		include the MAC address of the station that has authenticated."

    ::= { apNotificationTrapObjects 9 }

dot1xMacAddrAuthFail NOTIFICATION-TYPE
        OBJECTS { apNotificationDot11Station }
        STATUS current
        DESCRIPTION
        
		"The 802.1x MAC address authentication failure notification shall 
		be sent when a station fails to authenticate the MAC address
		with the RADIUS server. The value of the notification shall 
		include the MAC address of the station that failed to authenticate."

    ::= { apNotificationTrapObjects 10 }

dot1xAuthNotInitiated NOTIFICATION-TYPE
        OBJECTS { apNotificationDot11Station }
        STATUS current
        DESCRIPTION
        
		"The 802.1x authentication not initiated notification shall 
		be sent when a station did not initiate 802.1x authentication
		with the RADIUS server. The value of the notification shall 
		include the MAC address of the station that did not initiate 
		802.1x authentication."

    ::= { apNotificationTrapObjects 11 }

dot1xAuthSuccess NOTIFICATION-TYPE
        OBJECTS { apNotificationDot11Station }
        STATUS current
        DESCRIPTION
        
		"The 802.1x authentication success notification shall 
		be sent when a station successfully authenticates with the 
		RADIUS server. The value of the notification shall include 
		the MAC address of the station that has authenticated."

    ::= { apNotificationTrapObjects 12 }

dot1xAuthFail NOTIFICATION-TYPE
        OBJECTS { apNotificationDot11Station }
        STATUS current
        DESCRIPTION
        
		"The 802.1x authentication failure notification shall 
		be sent when a station fails to authenticate with the 
		RADIUS server. The value of the notification shall include 
		the MAC address of the station that failed to authenticate."

    ::= { apNotificationTrapObjects 13 }

localMacAddrAuthSuccess NOTIFICATION-TYPE
        OBJECTS { apNotificationDot11Station }
        STATUS current
        DESCRIPTION
        
		"The Local MAC address authentication success notification shall 
		be sent when a station successfully authenticates the MAC address
		with the database stored locally within the AP. The value of the 
		notification shall include the MAC address of the station that 
		has authenticated."

    ::= { apNotificationTrapObjects 14 }

localMacAddrAuthFail NOTIFICATION-TYPE
        OBJECTS { apNotificationDot11Station }
        STATUS current
        DESCRIPTION
        
		"The Local MAC address authentication failure notification shall 
		be sent when a station fails to authenticate the MAC address
		with the database stored locally within the AP. The value of the 
		notification shall include the MAC address of the station that 
		has authenticated."

    ::= { apNotificationTrapObjects 15 }

pppLogonFail NOTIFICATION-TYPE
--        OBJECTS { }
        STATUS current
        DESCRIPTION
        
		"The PPP Logon failure notification shall be sent out when 
		the AP fails to login successfully to the PPP peer using the 
		supplied username and password."

    ::= { apNotificationTrapObjects 16 }

iappStationRoamedFrom NOTIFICATION-TYPE
        OBJECTS { apNotificationDot11Station, apNotificationDot11IpAddress}
        STATUS current
        DESCRIPTION
        
		"The IAPP Station Roamed-From Notification shall be sent out
		 whenever a station roams from another Access Point (AP) to 
		 this AP. The notification shall include the MAC address of 
		 the station and the IP address of the old AP."

    ::= { apNotificationTrapObjects 17 }

iappStationRoamedTo NOTIFICATION-TYPE
        OBJECTS { apNotificationDot11Station, apNotificationDot11IpAddress}
        STATUS current
        DESCRIPTION
        
		"The IAPP Station Roamed-To Notification shall be sent out
		 whenever a station roams to another Access Point (AP) from 
		 this AP. The notification shall include the MAC address of 
		 the station and the IP address of the new AP."

    ::= { apNotificationTrapObjects 18 }


iappContextDataSent NOTIFICATION-TYPE
        OBJECTS { apNotificationDot11Station, apNotificationDot11IpAddress}
        STATUS current
        DESCRIPTION
        
		"The IAPP Context Data Sent notification shall be sent out
		 whenever the context data for a station has been sent to 
		 the new AP with which the station has associated. The 
		 notification shall include the MAC address of 
		 the station and the IP address of the new AP."

    ::= { apNotificationTrapObjects 19 }

sntpServerFail NOTIFICATION-TYPE
--        OBJECTS { }
        STATUS current
        DESCRIPTION
        
		"The sntpServerFail notification shall be sent when the AP 
		fails to get time from the configured SNTP server."

    ::= { apNotificationTrapObjects 20 }

dot11InterfaceAFail NOTIFICATION-TYPE
--        OBJECTS { }
        STATUS current
        DESCRIPTION
        
		"The InterfaceAFail notification shall be sent out when 
		802.11a wireless interface has failed."

    ::= { apNotificationTrapObjects 21 }

dot11InterfaceGFail NOTIFICATION-TYPE
--        OBJECTS { }
        STATUS current
        DESCRIPTION
        
		"The InterfaceGFail notification shall be sent out when 
		802.11g wireless interface has failed."

    ::= { apNotificationTrapObjects 22 }
-- -------------------------------------------------------------
-- -END:: apNotificationTrapTreebjects
-- -------------------------------------------------------------

END
