TRAP-TEST-MIB DEFINITIONS ::= BEGIN
	IMPORTS ucdExperimental FROM UCD-SNMP-MIB;

demotraps OBJECT IDENTIFIER ::= { ucdExperimental 990 }

demo-trap TRAP-TYPE
	STATUS current
	ENTERPRISE demotraps
	VARIABLES { sysLocation }
	DESCRIPTION "This is just a demo"
	::= 17

END
