DX-STATS-MIB DEFINITIONS ::= BEGIN

-- Title:	DX-STATS-MIB for SNMPv2
-- Date:	September 02, 2004
-- By:		Yogendra Singh <yogi@juniper.net>
--
-- Note: this MIB is Read-Only.
--		Added Forwarder SSL stats to the MIB.
-- $Rl: DX-STATS-MIB.txt,v 1.18.2.1 2007/09/05 19:18:54 chang Exp $`
--

IMPORTS MODULE-IDENTITY, OBJECT-TYPE, Counter64, Integer32
                FROM SNMPv2-SMI
        DisplayString 
                FROM SNMPv2-TC
        dx 
                FROM DX-MIB;

---------------------------------------------------------------------------
-- Stats Sub-Section
---------------------------------------------------------------------------
-- dxStats OBJECT IDENTIFIER ::= { dx 4 }
dxStats MODULE-IDENTITY
    LAST-UPDATED "200508032326Z"
    ORGANIZATION "Juniper Networks, Inc."
    CONTACT-INFO 
        "Contact: Juniper Networks Support
         Web: www.juniper.net
         Email: support@juniper.net
         Phone: 1.888.JUNIPER (888-586-4737) (Toll Free)
                1.408.745.2000 (Main)
                1.408.745.2100 (Fax)
         Postal: Juniper Networks Inc.,
                1194 North Mathilda Avenue
                Sunnyvale, California 94089-1206 
                 USA"
    DESCRIPTION
        "The statistics MIB module for the DX product of
         Juniper Networks, Inc.
         Copyright 2003-2005 Redline Networks, Inc. All rights reserved.
         Copyright 2005 Juniper Networks, Inc. All rights reserved."

    REVISION	"200310131945Z"
    DESCRIPTION
        "1) Fixed syntax errors
        2) Added new request methods"

    REVISION	"200309232332Z"
    DESCRIPTION
        "Added new browser types"

    REVISION	"200305310035Z"
    DESCRIPTION
        "Initial Version"

    ::= { dx 4 }

---------------------------------------------------------------------------
-- System Level Statistics
---------------------------------------------------------------------------
systemStats OBJECT IDENTIFIER ::= { dxStats 1 }

---------------------------------------------------------------------------
-- Statistics displayed by Dash Board.
---------------------------------------------------------------------------

---------------------------------------------------------------------------
-- Session Statistics
---------------------------------------------------------------------------
sessions OBJECT IDENTIFIER ::= { systemStats 1 }

sessActive OBJECT-TYPE
        SYNTAX     Counter64
        MAX-ACCESS read-only
        STATUS     current
        DESCRIPTION
            "The active number of sessions."
        ::= { sessions 1 }

sessTotal OBJECT-TYPE
        SYNTAX     Counter64
        MAX-ACCESS read-only
        STATUS     current
        DESCRIPTION
            "The total number of sessions handled."
        ::= { sessions 2 }

---------------------------------------------------------------------------
-- Request Statistics
---------------------------------------------------------------------------
requests OBJECT IDENTIFIER ::= { systemStats 2 }

reqActive OBJECT-TYPE
        SYNTAX     Counter64
        MAX-ACCESS read-only
        STATUS     current
        DESCRIPTION
            "The active number of requests."
        ::= { requests 1 }

reqTotal OBJECT-TYPE
        SYNTAX     Counter64
        MAX-ACCESS read-only
        STATUS     current
        DESCRIPTION
            "The total number of requests."
        ::= { requests 2 }

---------------------------------------------------------------------------
-- Byte Statistics
---------------------------------------------------------------------------
bytes OBJECT IDENTIFIER ::= { systemStats 3 }

bytesIn OBJECT-TYPE
        SYNTAX     Counter64
        MAX-ACCESS read-only
        STATUS     current
        DESCRIPTION
            "Total number of bytes in."
        ::= { bytes 1 }

bytesOut OBJECT-TYPE
        SYNTAX     Counter64
        MAX-ACCESS read-only
        STATUS     current
        DESCRIPTION
            "Total number of bytes out."
        ::= { bytes 2 }

---------------------------------------------------------------------------
-- Device Performance Statistics
---------------------------------------------------------------------------
devicePerformance OBJECT IDENTIFIER ::= { systemStats 4 }

duration OBJECT-TYPE
        SYNTAX     Counter64
        MAX-ACCESS read-only
        STATUS     current
        DESCRIPTION
            "The performance results calcuated over this duration (seconds)."
        ::= { devicePerformance 1 }

connectionsAccepted OBJECT-TYPE
        SYNTAX     Counter64
        MAX-ACCESS read-only
        STATUS     current
        DESCRIPTION
            "Total number of connections accepted." 
        ::= { devicePerformance 2 }

connectionsRefused OBJECT-TYPE
        SYNTAX     Counter64
        MAX-ACCESS read-only
        STATUS     current
        DESCRIPTION
            "Total number of connections refused."
        ::= { devicePerformance 3 }

requestsProcessed OBJECT-TYPE
        SYNTAX     Counter64
        MAX-ACCESS read-only
        STATUS     current
        DESCRIPTION
            "Total number of requests processed."
        ::= { devicePerformance 4 }

bytesSaved OBJECT-TYPE
        SYNTAX     Counter64
        MAX-ACCESS read-only
        STATUS     current
        DESCRIPTION
            "Total number of bytes saved till now."
        ::= { devicePerformance 5 }

avgConnectionsPerDay OBJECT-TYPE
        SYNTAX     Counter64
        MAX-ACCESS read-only
        STATUS     current
        DESCRIPTION
            "Average number of new connections per day."
        ::= { devicePerformance 6 }

avgRequestsPerDay OBJECT-TYPE
        SYNTAX     Counter64
        MAX-ACCESS read-only
        STATUS     current
        DESCRIPTION
            "Average number of new requests per day."
        ::= { devicePerformance 7 }

avgBytesSavedPerDay OBJECT-TYPE
        SYNTAX     Counter64
        MAX-ACCESS read-only
        STATUS     current
        DESCRIPTION
            "Average number of bytes saved per day."
        ::= { devicePerformance 8 }

avgCPUUsed OBJECT-TYPE
        SYNTAX     Integer32
        MAX-ACCESS read-only
        STATUS     current
        DESCRIPTION
            "Average cpu usage (percentage)."
        ::= { devicePerformance 9 }

avgMemoryUsed OBJECT-TYPE
        SYNTAX     Integer32
        MAX-ACCESS read-only
        STATUS     current
        DESCRIPTION
            "Average memory usage (percentage)."
        ::= { devicePerformance 10 }

---------------------------------------------------------------------------
-- Ether N Table
---------------------------------------------------------------------------
etherNTable OBJECT-TYPE
        SYNTAX     SEQUENCE OF EtherNEntry
        MAX-ACCESS not-accessible
        STATUS     current
        DESCRIPTION
            "The (conceptual) table listing all Ether N stats."
        ::= { devicePerformance 11 }

etherNEntry OBJECT-TYPE
        SYNTAX     EtherNEntry
        MAX-ACCESS not-accessible
        STATUS     current
        DESCRIPTION
            "An entry (conceptual row) in the etherNTable."
        INDEX      { etherNIndex }
        ::= { etherNTable 1 }


EtherNEntry ::=
        SEQUENCE {
            etherNIndex
                Integer32,
            etherNNumber
                Integer32,
            etherNBytesIn
                Counter64,
            etherNBytesOut
                Counter64
        }

etherNIndex OBJECT-TYPE
        SYNTAX     Integer32
        MAX-ACCESS  read-only
        STATUS     current
        DESCRIPTION
            "The auxiliary variable used for identifying instances of
            the columnar objects in the Ether N table."
        ::= { etherNEntry 1 }

etherNNumber OBJECT-TYPE
        SYNTAX     Integer32
        MAX-ACCESS  read-only
        STATUS     current
        DESCRIPTION
            "The current ether sequence id."
        ::= { etherNEntry 2 }

etherNBytesIn OBJECT-TYPE
        SYNTAX     Counter64
        MAX-ACCESS  read-only
        STATUS     current
        DESCRIPTION
            "Average bytes in (bytes/sec)."
        ::= { etherNEntry 3 }

etherNBytesOut OBJECT-TYPE
        SYNTAX     Counter64
        MAX-ACCESS  read-only
        STATUS     current
        DESCRIPTION
            "Average bytes out (bytes/sec)."
        ::= { etherNEntry 4 }


---------------------------------------------------------------------------
-- Cluster Level Statistics
---------------------------------------------------------------------------
clusterStats OBJECT IDENTIFIER ::= { dxStats 2 }

clusterIOStatsTable OBJECT-TYPE
        SYNTAX     SEQUENCE OF ClusterIOStatsEntry
        MAX-ACCESS not-accessible
        STATUS     current
        DESCRIPTION
            "The (conceptual) table listing the clusters IO stats."
        ::= { clusterStats 1 }

clusterIOStatsEntry OBJECT-TYPE
        SYNTAX     ClusterIOStatsEntry
        MAX-ACCESS not-accessible
        STATUS     current
        DESCRIPTION
            "An entry (conceptual row) in the clusterIOStats table."
        INDEX      { clusterIOStatsIndex }
        ::= { clusterIOStatsTable 1 }

ClusterIOStatsEntry ::=
        SEQUENCE {
        clusterIOStatsIndex 
           Integer32,
        clusterIOStatsListenSessionActive 
           Counter64,
        clusterIOStatsListenSessionTotal 
           Counter64,
        clusterIOStatsListenSessionRefused 
           Counter64,
        clusterIOStatsListenReqActive 
           Counter64,
        clusterIOStatsListenReqTotal 
           Counter64,
        clusterIOStatsListenBytesIn 
           Counter64,
        clusterIOStatsListenBytesOut 
           Counter64,
        clusterIOStatsTargetBytesIn 
           Counter64,
        clusterIOStatsTargetBytesOut 
           Counter64,
        clusterIOStatsListenDeadStickyThost 
           Counter64,
        clusterIOStatsListenDeletedStickyThost 
           Counter64,
        clusterIOStatsTargetDownStickyThost 
           Counter64
        }

---------------------------------------------------------------------------
-- Session Statistics
---------------------------------------------------------------------------
clusterIOStatsIndex OBJECT-TYPE
        SYNTAX     Integer32 (0..2147483647)
        MAX-ACCESS not-accessible
        STATUS     current
        DESCRIPTION
            "The Cluster Index"
        ::= { clusterIOStatsEntry 1 }

clusterIOStatsListenSessionActive OBJECT-TYPE
        SYNTAX     Counter64
        MAX-ACCESS read-only
        STATUS     current
        DESCRIPTION
            "The active number of sessions."
        ::= { clusterIOStatsEntry 2 }

clusterIOStatsListenSessionTotal OBJECT-TYPE
        SYNTAX     Counter64
        MAX-ACCESS read-only
        STATUS     current
        DESCRIPTION
            "The total number of sessions handled."
        ::= { clusterIOStatsEntry 3 }

clusterIOStatsListenSessionRefused OBJECT-TYPE
        SYNTAX     Counter64
        MAX-ACCESS read-only
        STATUS     current
        DESCRIPTION
            "The total number of sessions refused."
        ::= { clusterIOStatsEntry 4 }

---------------------------------------------------------------------------
-- Request Statistics
---------------------------------------------------------------------------
clusterIOStatsListenReqActive OBJECT-TYPE
        SYNTAX     Counter64
        MAX-ACCESS read-only
        STATUS     deprecated
        DESCRIPTION
            "The active number of requests."
        ::= { clusterIOStatsEntry 5 }

clusterIOStatsListenReqTotal OBJECT-TYPE
        SYNTAX     Counter64
        MAX-ACCESS read-only
        STATUS     deprecated
        DESCRIPTION
            "The total number of requests."
        ::= { clusterIOStatsEntry 6 }

---------------------------------------------------------------------------
-- Byte Statistics
---------------------------------------------------------------------------
clusterIOStatsListenBytesIn OBJECT-TYPE
        SYNTAX     Counter64
        MAX-ACCESS read-only
        STATUS     current
        DESCRIPTION
            "Total number of bytes in."
        ::= { clusterIOStatsEntry 7 }

clusterIOStatsListenBytesOut OBJECT-TYPE
        SYNTAX     Counter64
        MAX-ACCESS read-only
        STATUS     current
        DESCRIPTION
            "Total number of bytes out."
        ::= { clusterIOStatsEntry 8 }


clusterIOStatsTargetBytesIn OBJECT-TYPE
        SYNTAX     Counter64
        MAX-ACCESS read-only
        STATUS     current
        DESCRIPTION
            "Total number of bytes in."
        ::= { clusterIOStatsEntry 9 }

clusterIOStatsTargetBytesOut OBJECT-TYPE
        SYNTAX     Counter64
        MAX-ACCESS read-only
        STATUS     current
        DESCRIPTION
            "Total number of bytes out."
        ::= { clusterIOStatsEntry 10 }

clusterIOStatsListenDeadStickyThost OBJECT-TYPE
        SYNTAX     Counter64
        MAX-ACCESS read-only
        STATUS     current
        DESCRIPTION
            "Number of times client IP sticky target was dead."
        ::= { clusterIOStatsEntry 11 }

clusterIOStatsListenDeletedStickyThost OBJECT-TYPE
        SYNTAX     Counter64
        MAX-ACCESS read-only
        STATUS     current
        DESCRIPTION
            "Number of times client IP sticky target was deleted."
        ::= { clusterIOStatsEntry 12 }

clusterIOStatsTargetDownStickyThost OBJECT-TYPE
        SYNTAX     Counter64
        MAX-ACCESS read-only
        STATUS     current
        DESCRIPTION
            "Number of times client IP sticky target service was down."
        ::= { clusterIOStatsEntry 13 }

---------------------------------------------------------------------------
-- HTTP Statistics per cluster
---------------------------------------------------------------------------
clusterHTTPStatsTable OBJECT-TYPE
        SYNTAX     SEQUENCE OF ClusterHTTPStatsEntry
        MAX-ACCESS not-accessible
        STATUS     current
        DESCRIPTION
            "The (conceptual) table listing the clusters HTTP stats."
        ::= { clusterStats 2 }

clusterHTTPStatsEntry OBJECT-TYPE
        SYNTAX     ClusterHTTPStatsEntry
        MAX-ACCESS not-accessible
        STATUS     current
        DESCRIPTION
            "An entry (conceptual row) in the clusterHTTPStats table."
        INDEX      { clusterHTTPStatsIndex }
        ::= { clusterHTTPStatsTable 1 }

ClusterHTTPStatsEntry ::=
        SEQUENCE {
        clusterHTTPStatsIndex 
           Integer32,
        clusterHTTPStatsListenReqActive 
           Counter64,
        clusterHTTPStatsListenReqTotal 
           Counter64,

        clusterHTTPStatsListenGETReq 
           Counter64,
        clusterHTTPStatsListenPOSTReq 
           Counter64,
        clusterHTTPStatsListenHEADReq 
           Counter64,
        clusterHTTPStatsListenOtherReq 
           Counter64,
        clusterHTTPStatsListenHTTP10Req 
           Counter64,
        clusterHTTPStatsListenHTTP11Req 
           Counter64,
        clusterHTTPStatsListenUnknownHTTPVersionReq 
           Counter64,

        clusterHTTPStatsListenIllegalMethod 
           Counter64,
        clusterHTTPStatsListenIllegalHEADReq 
           Counter64,
        clusterHTTPStatsListenIllegalPOST 
           Counter64,
        clusterHTTPStatsListenIllegalHeader 
           Counter64,
        clusterHTTPStatsListenIllegalHeaderTooLong 
           Counter64,

        clusterHTTPStatsListenBrowserIE60 
           Counter64,
        clusterHTTPStatsListenBrowserIE55 
           Counter64,
        clusterHTTPStatsListenBrowserIE50 
           Counter64,
        clusterHTTPStatsListenBrowserIE4x 
           Counter64,
        clusterHTTPStatsListenBrowserIEOther 
           Counter64,
        clusterHTTPStatsListenBrowserNetscape 
           Counter64,
        clusterHTTPStatsListenBrowserOpera 
           Counter64,
        clusterHTTPStatsListenBrowserOther 
           Counter64,

        clusterHTTPStatsTargetResponseCode100 
           Counter64,
        clusterHTTPStatsTargetResponseCode200 
           Counter64,
        clusterHTTPStatsTargetResponseCode302 
           Counter64,
        clusterHTTPStatsTargetResponseCode304 
           Counter64,
        clusterHTTPStatsTargetResponseCode3xx 
           Counter64,
        clusterHTTPStatsTargetResponseCode404 
           Counter64,
        clusterHTTPStatsTargetResponseCode4xx
           Counter64,
        clusterHTTPStatsTargetResponseCode5xx
           Counter64,
        clusterHTTPStatsTargetResponseCodeOthers
           Counter64,

        clusterHTTPStatsTargetContentGIF
           Counter64,
        clusterHTTPStatsTargetContentJPEG
           Counter64,
        clusterHTTPStatsTargetContentHTML
           Counter64,
        clusterHTTPStatsTargetContentCSS
           Counter64,
        clusterHTTPStatsTargetContentXML
           Counter64,
        clusterHTTPStatsTargetContentTEXT
           Counter64,
        clusterHTTPStatsTargetContentJAVASCRIPT
           Counter64,
        clusterHTTPStatsTargetContentFLASH
           Counter64,
        clusterHTTPStatsTargetContentOthers
           Counter64,

        clusterHTTPStatsTargetBytesInGIF
           Counter64,
        clusterHTTPStatsTargetBytesInJPEG
           Counter64,
        clusterHTTPStatsTargetBytesInHTML
           Counter64,
        clusterHTTPStatsTargetBytesInCSS
           Counter64,
        clusterHTTPStatsTargetBytesInXML
           Counter64,
        clusterHTTPStatsTargetBytesInTEXT
           Counter64,
        clusterHTTPStatsTargetBytesInJAVASCRIPT
           Counter64,
        clusterHTTPStatsTargetBytesInFLASH
           Counter64,
        clusterHTTPStatsTargetBytesInOthers
           Counter64,

        clusterHTTPStatsTargetBytesOutGIF
           Counter64,
        clusterHTTPStatsTargetBytesOutJPEG
           Counter64,
        clusterHTTPStatsTargetBytesOutHTML
           Counter64,
        clusterHTTPStatsTargetBytesOutCSS
           Counter64,
        clusterHTTPStatsTargetBytesOutXML
           Counter64,
        clusterHTTPStatsTargetBytesOutTEXT
           Counter64,
        clusterHTTPStatsTargetBytesOutJAVASCRIPT
           Counter64,
        clusterHTTPStatsTargetBytesOutFLASH
           Counter64,
        clusterHTTPStatsTargetBytesOutOthers
           Counter64,

        clusterHTTPStatsListenBrowserIE51
           Counter64,
        clusterHTTPStatsListenBrowserNetscape6
           Counter64,
        clusterHTTPStatsListenBrowserMozilla
           Counter64,
        clusterHTTPStatsListenBrowserKonquerer
           Counter64,
        clusterHTTPStatsListenBrowserSafari
           Counter64,
        clusterHTTPStatsListenBrowserNone
           Counter64,

        clusterHTTPStatsListenPUTReq 
           Counter64,
        clusterHTTPStatsListenDELETEReq 
           Counter64,
        clusterHTTPStatsListenTRACEReq 
           Counter64,
        clusterHTTPStatsListenOPTIONSReq 
           Counter64,
        clusterHTTPStatsListenCONNECTReq 
           Counter64,
        clusterHTTPStatsListenPROPFINDReq 
           Counter64,
        clusterHTTPStatsListenPROPPATCHReq 
           Counter64,
        clusterHTTPStatsListenMKCOLReq 
           Counter64,
        clusterHTTPStatsListenCOPYReq 
           Counter64,
        clusterHTTPStatsListenMOVEReq 
           Counter64,
        clusterHTTPStatsListenLOCKReq 
           Counter64,
        clusterHTTPStatsListenUNLOCKReq 
           Counter64,
        clusterHTTPStatsListenBCOPYReq 
           Counter64,
        clusterHTTPStatsListenBDELETEReq 
           Counter64,
        clusterHTTPStatsListenBMOVEReq 
           Counter64,
        clusterHTTPStatsListenBPROPFINDReq 
           Counter64,
        clusterHTTPStatsListenBPROPPATCHReq 
           Counter64,
        clusterHTTPStatsListenNOTIFYReq 
           Counter64,
        clusterHTTPStatsListenPOLLReq 
           Counter64,
        clusterHTTPStatsListenSEARCHReq 
           Counter64,
        clusterHTTPStatsListenSUBSCRIBEReq 
           Counter64,
        clusterHTTPStatsListenUNSUBSCRIBEReq 
           Counter64,
        clusterHTTPStatsListenXMSENUMATTSReq 
           Counter64,
        clusterHTTPStatsListenVERSIONCONTROLReq 
           Counter64,
        clusterHTTPStatsListenREPORTReq 
           Counter64,
        clusterHTTPStatsListenCHECKOUTReq 
           Counter64,
        clusterHTTPStatsListenCHECKINReq 
           Counter64,
        clusterHTTPStatsListenUNCHECKOUTReq 
           Counter64,
        clusterHTTPStatsListenMKWORKSPACEReq 
           Counter64,
        clusterHTTPStatsListenUPDATEReq 
           Counter64,
        clusterHTTPStatsListenLABELReq 
           Counter64,
        clusterHTTPStatsListenMERGEReq 
           Counter64,
        clusterHTTPStatsListenBASELINECONTROLReq 
           Counter64,
        clusterHTTPStatsListenMKACTIVITYReq 
           Counter64,
        clusterHTTPStatsListenBINDReq 
           Counter64,
        clusterHTTPStatsListenMKRESOURCEReq 
           Counter64,
        clusterHTTPStatsListenORDERPATCHReq 
           Counter64,
        clusterHTTPStatsListenACLReq 
           Counter64,

        clusterHTTPStatsTargetResponseCode1xx
           Counter64,
        clusterHTTPStatsTargetResponseCode101
           Counter64,
        clusterHTTPStatsTargetResponseCode102
           Counter64,

        clusterHTTPStatsTargetResponseCode2xx
           Counter64,
        clusterHTTPStatsTargetResponseCode201
           Counter64,
        clusterHTTPStatsTargetResponseCode202
           Counter64,
        clusterHTTPStatsTargetResponseCode203
           Counter64,
        clusterHTTPStatsTargetResponseCode204
           Counter64,
        clusterHTTPStatsTargetResponseCode205
           Counter64,
        clusterHTTPStatsTargetResponseCode206
           Counter64,
        clusterHTTPStatsTargetResponseCode207
           Counter64,

        clusterHTTPStatsTargetResponseCode300
           Counter64,
        clusterHTTPStatsTargetResponseCode301
           Counter64,
        clusterHTTPStatsTargetResponseCode303
           Counter64,
        clusterHTTPStatsTargetResponseCode305
           Counter64,
        clusterHTTPStatsTargetResponseCode306
           Counter64,
        clusterHTTPStatsTargetResponseCode307
           Counter64,

        clusterHTTPStatsTargetResponseCode400
           Counter64,
        clusterHTTPStatsTargetResponseCode401
           Counter64,
        clusterHTTPStatsTargetResponseCode402
           Counter64,
        clusterHTTPStatsTargetResponseCode403
           Counter64,
        clusterHTTPStatsTargetResponseCode405
           Counter64,
        clusterHTTPStatsTargetResponseCode406
           Counter64,
        clusterHTTPStatsTargetResponseCode407
           Counter64,
        clusterHTTPStatsTargetResponseCode408
           Counter64,
        clusterHTTPStatsTargetResponseCode409
           Counter64,
        clusterHTTPStatsTargetResponseCode410
           Counter64,
        clusterHTTPStatsTargetResponseCode411
           Counter64,
        clusterHTTPStatsTargetResponseCode412
           Counter64,
        clusterHTTPStatsTargetResponseCode413
           Counter64,
        clusterHTTPStatsTargetResponseCode414
           Counter64,
        clusterHTTPStatsTargetResponseCode415
           Counter64,
        clusterHTTPStatsTargetResponseCode416
           Counter64,
        clusterHTTPStatsTargetResponseCode417
           Counter64,
        clusterHTTPStatsTargetResponseCode422
           Counter64,
        clusterHTTPStatsTargetResponseCode423
           Counter64,
        clusterHTTPStatsTargetResponseCode424
           Counter64,
        clusterHTTPStatsTargetResponseCode425
           Counter64,

        clusterHTTPStatsTargetResponseCode500
           Counter64,
        clusterHTTPStatsTargetResponseCode501
           Counter64,
        clusterHTTPStatsTargetResponseCode502
           Counter64,
        clusterHTTPStatsTargetResponseCode503
           Counter64,
        clusterHTTPStatsTargetResponseCode504
           Counter64,
        clusterHTTPStatsTargetResponseCode505
           Counter64,
        clusterHTTPStatsTargetResponseCode506
           Counter64,
        clusterHTTPStatsTargetResponseCode507
           Counter64,

        clusterHTTPStatsTargetContentXCOMPONENT
           Counter64,
        clusterHTTPStatsTargetContentOCTETSTREAM
           Counter64,
        clusterHTTPStatsTargetContentMSWORD
           Counter64,
        clusterHTTPStatsTargetContentMSEXCEL
           Counter64,
        clusterHTTPStatsTargetContentMSPOWERPOINT
           Counter64,
        clusterHTTPStatsTargetContentCUSTOM1
           Counter64,
        clusterHTTPStatsTargetContentCUSTOM2
           Counter64,
        clusterHTTPStatsTargetContentCUSTOM3
           Counter64,

        clusterHTTPStatsTargetBytesInXCOMPONENT
           Counter64,
        clusterHTTPStatsTargetBytesInOCTETSTREAM
           Counter64,
        clusterHTTPStatsTargetBytesInMSWORD
           Counter64,
        clusterHTTPStatsTargetBytesInMSEXCEL
           Counter64,
        clusterHTTPStatsTargetBytesInMSPOWERPOINT
           Counter64,
        clusterHTTPStatsTargetBytesInCUSTOM1
           Counter64,
        clusterHTTPStatsTargetBytesInCUSTOM2
           Counter64,
        clusterHTTPStatsTargetBytesInCUSTOM3
           Counter64,

        clusterHTTPStatsTargetBytesOutXCOMPONENT
           Counter64,
        clusterHTTPStatsTargetBytesOutOCTETSTREAM
           Counter64,
        clusterHTTPStatsTargetBytesOutMSWORD
           Counter64,
        clusterHTTPStatsTargetBytesOutMSEXCEL
           Counter64,
        clusterHTTPStatsTargetBytesOutMSPOWERPOINT
           Counter64,
        clusterHTTPStatsTargetBytesOutCUSTOM1
           Counter64,
        clusterHTTPStatsTargetBytesOutCUSTOM2
           Counter64,
        clusterHTTPStatsTargetBytesOutCUSTOM3
           Counter64,

        clusterHTTPStatsTargetDecompressionPerformed
           Counter64,
        clusterHTTPStatsTargetDecompressionFailure
           Counter64,

        clusterHTTPStatsListenIllegalHeaderLimitReached 
           Counter64,
        clusterHTTPStatsTargetCompressContentGIF
            Counter64,
        clusterHTTPStatsTargetCompressContentJPEG
            Counter64,
        clusterHTTPStatsTargetCompressContentHTML
            Counter64,
        clusterHTTPStatsTargetCompressContentCSS
            Counter64,
        clusterHTTPStatsTargetCompressContentXML
            Counter64,
        clusterHTTPStatsTargetCompressContentPLAIN
            Counter64,
        clusterHTTPStatsTargetCompressContentXCOMPONENT
            Counter64,
        clusterHTTPStatsTargetCompressContentJAVASCRIPT
            Counter64,
        clusterHTTPStatsTargetCompressContentFLASH
            Counter64,
        clusterHTTPStatsTargetCompressContentOCTETSTREAM
            Counter64,
        clusterHTTPStatsTargetCompressContentMSWORD
            Counter64,
        clusterHTTPStatsTargetCompressContentMSEXCEL
            Counter64,
        clusterHTTPStatsTargetCompressContentMSPOWERPOINT
            Counter64,
        clusterHTTPStatsTargetCompressContentCUSTOM1
            Counter64,
        clusterHTTPStatsTargetCompressContentCUSTOM2
            Counter64,
        clusterHTTPStatsTargetCompressContentCUSTOM3
            Counter64,
        clusterHTTPStatsTargetCompressContentOTHER
            Counter64,

       clusterHTTPStatsListenReqWithUnexpectedBody
           Counter64,
       clusterHTTPStatsListenReqBodyExceededLimit
           Counter64,
       clusterHTTPStatsListenIllegalMultiContentLengthHeader 
           Counter64,

        clusterHTTPStatsListenBrowserIE70
           Counter64
        }

---------------------------------------------------------------------------
-- Request Statistics
---------------------------------------------------------------------------
clusterHTTPStatsIndex OBJECT-TYPE
        SYNTAX     Integer32 (0..2147483647)
        MAX-ACCESS not-accessible
        STATUS     current
        DESCRIPTION
            "The Cluster Index"
        ::= { clusterHTTPStatsEntry 1 }

clusterHTTPStatsListenReqActive OBJECT-TYPE
        SYNTAX     Counter64
        MAX-ACCESS read-only
        STATUS     current
        DESCRIPTION
            "The active number of requests."
        ::= { clusterHTTPStatsEntry 2 }

clusterHTTPStatsListenReqTotal OBJECT-TYPE
        SYNTAX     Counter64
        MAX-ACCESS read-only
        STATUS     current
        DESCRIPTION
            "The total number of requests."
        ::= { clusterHTTPStatsEntry 3 }

clusterHTTPStatsListenGETReq OBJECT-TYPE
        SYNTAX     Counter64
        MAX-ACCESS read-only
        STATUS     current
        DESCRIPTION
            "The total number of GET HTTP requests."
        ::= { clusterHTTPStatsEntry 4 }

clusterHTTPStatsListenPOSTReq OBJECT-TYPE
        SYNTAX     Counter64
        MAX-ACCESS read-only
        STATUS     current
        DESCRIPTION
            "The total number of POST HTTP requests."
        ::= { clusterHTTPStatsEntry 5 }

clusterHTTPStatsListenHEADReq OBJECT-TYPE
        SYNTAX     Counter64
        MAX-ACCESS read-only
        STATUS     current
        DESCRIPTION
            "The total number of HEAD HTTP requests."
        ::= { clusterHTTPStatsEntry 6 }

clusterHTTPStatsListenOtherReq OBJECT-TYPE
        SYNTAX     Counter64
        MAX-ACCESS read-only
        STATUS     current
        DESCRIPTION
            "The total number of Other HTTP requests."
        ::= { clusterHTTPStatsEntry 7 }

clusterHTTPStatsListenHTTP10Req OBJECT-TYPE
        SYNTAX     Counter64
        MAX-ACCESS read-only
        STATUS     current
        DESCRIPTION
            "The total number of HTTP/1.0 requests."
        ::= { clusterHTTPStatsEntry 8 }

clusterHTTPStatsListenHTTP11Req OBJECT-TYPE
        SYNTAX     Counter64
        MAX-ACCESS read-only
        STATUS     current
        DESCRIPTION
            "The total number of HTTP/1.1 requests."
        ::= { clusterHTTPStatsEntry 9 }

clusterHTTPStatsListenUnknownHTTPVersionReq OBJECT-TYPE
        SYNTAX     Counter64
        MAX-ACCESS read-only
        STATUS     current
        DESCRIPTION
            "The total number of HTTP requests with non HTTP/1.0 and non HTTP/1.1 versions."
        ::= { clusterHTTPStatsEntry 10 }

clusterHTTPStatsListenIllegalMethod OBJECT-TYPE
        SYNTAX     Counter64
        MAX-ACCESS read-only
        STATUS     current
        DESCRIPTION
            "The number of illegal HTTP methods."
        ::= { clusterHTTPStatsEntry 11 }

clusterHTTPStatsListenIllegalHEADReq OBJECT-TYPE
        SYNTAX     Counter64
        MAX-ACCESS read-only
        STATUS     current
        DESCRIPTION
            "The number of HEAD request with HTTP/0.9."
        ::= { clusterHTTPStatsEntry 12 }

clusterHTTPStatsListenIllegalPOST OBJECT-TYPE
        SYNTAX     Counter64
        MAX-ACCESS read-only
        STATUS     current
        DESCRIPTION
            "The number of POST request with either length <= 0 or no length."
        ::= { clusterHTTPStatsEntry 13 }

clusterHTTPStatsListenIllegalHeader OBJECT-TYPE
        SYNTAX     Counter64
        MAX-ACCESS read-only
        STATUS     current
        DESCRIPTION
            "The number of requests with illegal HTTP header."
        ::= { clusterHTTPStatsEntry 14 }

clusterHTTPStatsListenIllegalHeaderTooLong OBJECT-TYPE
        SYNTAX     Counter64
        MAX-ACCESS read-only
        STATUS     current
        DESCRIPTION
            "The number of request with header line too long."
        ::= { clusterHTTPStatsEntry 15 }

clusterHTTPStatsListenIllegalHeaderLimitReached OBJECT-TYPE
        SYNTAX     Counter64
        MAX-ACCESS read-only
        STATUS     current
        DESCRIPTION
            "The number of request with headers that exceed server limit."
        ::= { clusterHTTPStatsEntry 176 }

clusterHTTPStatsListenIllegalMultiContentLengthHeader OBJECT-TYPE
        SYNTAX     Counter64
        MAX-ACCESS read-only
        STATUS     current
        DESCRIPTION
            "The number of request with multiple Content-Length header."
        ::= { clusterHTTPStatsEntry 196 }

clusterHTTPStatsListenReqWithUnexpectedBody OBJECT-TYPE
        SYNTAX     Counter64
        MAX-ACCESS read-only
        STATUS     current
        DESCRIPTION
            "The number of requests with unexpected request body."
        ::= { clusterHTTPStatsEntry 194 }

clusterHTTPStatsListenReqBodyExceededLimit OBJECT-TYPE
        SYNTAX     Counter64
        MAX-ACCESS read-only
        STATUS     current
        DESCRIPTION
            "The number of requests which had body that exceeded limit."
        ::= { clusterHTTPStatsEntry 195 }

clusterHTTPStatsListenBrowserIE70 OBJECT-TYPE
        SYNTAX     Counter64
        MAX-ACCESS read-only
        STATUS     current
        DESCRIPTION
            "The number of client requests from browser IE 7.0."
        ::= { clusterHTTPStatsEntry 197 }

clusterHTTPStatsListenBrowserIE60 OBJECT-TYPE
        SYNTAX     Counter64
        MAX-ACCESS read-only
        STATUS     current
        DESCRIPTION
            "The number of client requests from browser IE 6.0."
        ::= { clusterHTTPStatsEntry 16 }

clusterHTTPStatsListenBrowserIE55 OBJECT-TYPE
        SYNTAX     Counter64
        MAX-ACCESS read-only
        STATUS     current
        DESCRIPTION
            "The number of client requests from browser IE 5.5."
        ::= { clusterHTTPStatsEntry 17 }

clusterHTTPStatsListenBrowserIE50 OBJECT-TYPE
        SYNTAX     Counter64
        MAX-ACCESS read-only
        STATUS     current
        DESCRIPTION
            "The number of client requests from browser IE 5.0."
        ::= { clusterHTTPStatsEntry 18 }

clusterHTTPStatsListenBrowserIE4x OBJECT-TYPE
        SYNTAX     Counter64
        MAX-ACCESS read-only
        STATUS     current
        DESCRIPTION
            "The number of client requests from browser IE 4.x."
        ::= { clusterHTTPStatsEntry 19 }

clusterHTTPStatsListenBrowserIEOther OBJECT-TYPE
        SYNTAX     Counter64
        MAX-ACCESS read-only
        STATUS     current
        DESCRIPTION
            "The number of client requests from browser IE version other than (6.0/5.5/5.0/4.x)."
        ::= { clusterHTTPStatsEntry 20 }

clusterHTTPStatsListenBrowserNetscape OBJECT-TYPE
        SYNTAX     Counter64
        MAX-ACCESS read-only
        STATUS     current
        DESCRIPTION
            "The number of client requests from browser Netscape 4."
        ::= { clusterHTTPStatsEntry 21 }

clusterHTTPStatsListenBrowserOpera OBJECT-TYPE
        SYNTAX     Counter64
        MAX-ACCESS read-only
        STATUS     current
        DESCRIPTION
            "The number of client requests from browser Opera."
        ::= { clusterHTTPStatsEntry 22 }

clusterHTTPStatsListenBrowserOther OBJECT-TYPE
        SYNTAX     Counter64
        MAX-ACCESS read-only
        STATUS     current
        DESCRIPTION
            "The number of client requests from browsers not identified ."
        ::= { clusterHTTPStatsEntry 23 }

clusterHTTPStatsTargetResponseCode100 OBJECT-TYPE
        SYNTAX     Counter64
        MAX-ACCESS read-only
        STATUS     current
        DESCRIPTION
            "The total number of HTTP 100 response code."
        ::= { clusterHTTPStatsEntry 24 }

clusterHTTPStatsTargetResponseCode200 OBJECT-TYPE
        SYNTAX     Counter64
        MAX-ACCESS read-only
        STATUS     current
        DESCRIPTION
            "The total number of HTTP 200 response code."
        ::= { clusterHTTPStatsEntry 25 }

clusterHTTPStatsTargetResponseCode302 OBJECT-TYPE
        SYNTAX     Counter64
        MAX-ACCESS read-only
        STATUS     current
        DESCRIPTION
            "The total number of HTTP 302 response code."
        ::= { clusterHTTPStatsEntry 26 }

clusterHTTPStatsTargetResponseCode304 OBJECT-TYPE
        SYNTAX     Counter64
        MAX-ACCESS read-only
        STATUS     current
        DESCRIPTION
            "The total number of HTTP 304 response code."
        ::= { clusterHTTPStatsEntry 27 }

clusterHTTPStatsTargetResponseCode3xx OBJECT-TYPE
        SYNTAX     Counter64
        MAX-ACCESS read-only
        STATUS     current
        DESCRIPTION
            "The total number of HTTP 3xx response code."
        ::= { clusterHTTPStatsEntry 28 }

clusterHTTPStatsTargetResponseCode404 OBJECT-TYPE
        SYNTAX     Counter64
        MAX-ACCESS read-only
        STATUS     current
        DESCRIPTION
            "The total number of HTTP 404 response code."
        ::= { clusterHTTPStatsEntry 29 }

clusterHTTPStatsTargetResponseCode4xx OBJECT-TYPE
        SYNTAX     Counter64
        MAX-ACCESS read-only
        STATUS     current
        DESCRIPTION
            "The total number of HTTP 4xx response code."
        ::= { clusterHTTPStatsEntry 30 }

clusterHTTPStatsTargetResponseCode5xx OBJECT-TYPE
        SYNTAX     Counter64
        MAX-ACCESS read-only
        STATUS     current
        DESCRIPTION
            "The total number of HTTP 5xx response code."
        ::= { clusterHTTPStatsEntry 31 }

clusterHTTPStatsTargetResponseCodeOthers OBJECT-TYPE
        SYNTAX     Counter64
        MAX-ACCESS read-only
        STATUS     current
        DESCRIPTION
            "The total number of Others HTTP response codes."
        ::= { clusterHTTPStatsEntry 32 }

clusterHTTPStatsTargetContentGIF OBJECT-TYPE
        SYNTAX     Counter64
        MAX-ACCESS read-only
        STATUS     current
        DESCRIPTION
            "The total number of responses with content type GIF."
        ::= { clusterHTTPStatsEntry 33 }

clusterHTTPStatsTargetContentJPEG OBJECT-TYPE
        SYNTAX     Counter64
        MAX-ACCESS read-only
        STATUS     current
        DESCRIPTION
            "The total number of responses with content type JPEG."
        ::= { clusterHTTPStatsEntry 34 }

clusterHTTPStatsTargetContentHTML OBJECT-TYPE
        SYNTAX     Counter64
        MAX-ACCESS read-only
        STATUS     current
        DESCRIPTION
            "The total number of responses with content type HTML."
        ::= { clusterHTTPStatsEntry 35 }

clusterHTTPStatsTargetContentCSS OBJECT-TYPE
        SYNTAX     Counter64
        MAX-ACCESS read-only
        STATUS     current
        DESCRIPTION
            "The total number of responses with content type CSS."
        ::= { clusterHTTPStatsEntry 36 }

clusterHTTPStatsTargetContentXML OBJECT-TYPE
        SYNTAX     Counter64
        MAX-ACCESS read-only
        STATUS     current
        DESCRIPTION
            "The total number of responses with content type XML."
        ::= { clusterHTTPStatsEntry 37 }

clusterHTTPStatsTargetContentTEXT OBJECT-TYPE
        SYNTAX     Counter64
        MAX-ACCESS read-only
        STATUS     current
        DESCRIPTION
            "The total number of responses with content type TEXT."
        ::= { clusterHTTPStatsEntry 38 }

clusterHTTPStatsTargetContentJAVASCRIPT OBJECT-TYPE
        SYNTAX     Counter64
        MAX-ACCESS read-only
        STATUS     current
        DESCRIPTION
            "The total number of responses with content type JAVASCRIPT."
        ::= { clusterHTTPStatsEntry 39 }

clusterHTTPStatsTargetContentFLASH OBJECT-TYPE
        SYNTAX     Counter64
        MAX-ACCESS read-only
        STATUS     current
        DESCRIPTION
            "The total number of responses with content type FLASH."
        ::= { clusterHTTPStatsEntry 40 }

clusterHTTPStatsTargetContentOthers OBJECT-TYPE
        SYNTAX     Counter64
        MAX-ACCESS read-only
        STATUS     current
        DESCRIPTION
            "The total number of responses with non-listed content types."
        ::= { clusterHTTPStatsEntry 41 }

clusterHTTPStatsTargetBytesInGIF OBJECT-TYPE
        SYNTAX     Counter64
        MAX-ACCESS read-only
        STATUS     current
        DESCRIPTION
            "Total number of HTTP response body bytes received with the 
             given content type (excluding chunk headers) BEFORE the TX 
             performs its HTTP-level response body processing. HTTP response 
             headers and chunk headers/trailers are not counted, but any 
             compressed or uncompressed HTTP data is counted. Responses that 
             do not have a body (e.g. 304) are not counted."
        ::= { clusterHTTPStatsEntry 42 }

clusterHTTPStatsTargetBytesInJPEG OBJECT-TYPE
        SYNTAX     Counter64
        MAX-ACCESS read-only
        STATUS     current
        DESCRIPTION
            "Total number of HTTP response body bytes received with the 
             given content type (excluding chunk headers) BEFORE the TX 
             performs its HTTP-level response body processing. HTTP response 
             headers and chunk headers/trailers are not counted, but any 
             compressed or uncompressed HTTP data is counted. Responses that 
             do not have a body (e.g. 304) are not counted."
        ::= { clusterHTTPStatsEntry 43 }

clusterHTTPStatsTargetBytesInHTML OBJECT-TYPE
        SYNTAX     Counter64
        MAX-ACCESS read-only
        STATUS     current
        DESCRIPTION
            "Total number of HTTP response body bytes received with the 
             given content type (excluding chunk headers) BEFORE the TX 
             performs its HTTP-level response body processing. HTTP response 
             headers and chunk headers/trailers are not counted, but any 
             compressed or uncompressed HTTP data is counted. Responses that 
             do not have a body (e.g. 304) are not counted."
        ::= { clusterHTTPStatsEntry 44 }

clusterHTTPStatsTargetBytesInCSS OBJECT-TYPE
        SYNTAX     Counter64
        MAX-ACCESS read-only
        STATUS     current
        DESCRIPTION
            "Total number of HTTP response body bytes received with the 
             given content type (excluding chunk headers) BEFORE the TX 
             performs its HTTP-level response body processing. HTTP response 
             headers and chunk headers/trailers are not counted, but any 
             compressed or uncompressed HTTP data is counted. Responses that 
             do not have a body (e.g. 304) are not counted."
        ::= { clusterHTTPStatsEntry 45 }

clusterHTTPStatsTargetBytesInXML OBJECT-TYPE
        SYNTAX     Counter64
        MAX-ACCESS read-only
        STATUS     current
        DESCRIPTION
            "Total number of HTTP response body bytes received with the 
             given content type (excluding chunk headers) BEFORE the TX 
             performs its HTTP-level response body processing. HTTP response 
             headers and chunk headers/trailers are not counted, but any 
             compressed or uncompressed HTTP data is counted. Responses that 
             do not have a body (e.g. 304) are not counted."
        ::= { clusterHTTPStatsEntry 46 }

clusterHTTPStatsTargetBytesInTEXT OBJECT-TYPE
        SYNTAX     Counter64
        MAX-ACCESS read-only
        STATUS     current
        DESCRIPTION
            "Total number of HTTP response body bytes received with the 
             given content type (excluding chunk headers) BEFORE the TX 
             performs its HTTP-level response body processing. HTTP response 
             headers and chunk headers/trailers are not counted, but any 
             compressed or uncompressed HTTP data is counted. Responses that 
             do not have a body (e.g. 304) are not counted."
        ::= { clusterHTTPStatsEntry 47 }

clusterHTTPStatsTargetBytesInJAVASCRIPT OBJECT-TYPE
        SYNTAX     Counter64
        MAX-ACCESS read-only
        STATUS     current
        DESCRIPTION
            "Total number of HTTP response body bytes received with the 
             given content type (excluding chunk headers) BEFORE the TX 
             performs its HTTP-level response body processing. HTTP response 
             headers and chunk headers/trailers are not counted, but any 
             compressed or uncompressed HTTP data is counted. Responses that 
             do not have a body (e.g. 304) are not counted."
        ::= { clusterHTTPStatsEntry 48 }

clusterHTTPStatsTargetBytesInFLASH OBJECT-TYPE
        SYNTAX     Counter64
        MAX-ACCESS read-only
        STATUS     current
        DESCRIPTION
            "Total number of HTTP response body bytes received with the 
             given content type (excluding chunk headers) BEFORE the TX 
             performs its HTTP-level response body processing. HTTP response 
             headers and chunk headers/trailers are not counted, but any 
             compressed or uncompressed HTTP data is counted. Responses that 
             do not have a body (e.g. 304) are not counted."
        ::= { clusterHTTPStatsEntry 49 }

clusterHTTPStatsTargetBytesInOthers OBJECT-TYPE
        SYNTAX     Counter64
        MAX-ACCESS read-only
        STATUS     current
        DESCRIPTION
            "Total number of HTTP response body bytes received with the 
             given content type (excluding chunk headers) BEFORE the TX 
             performs its HTTP-level response body processing. HTTP response 
             headers and chunk headers/trailers are not counted, but any 
             compressed or uncompressed HTTP data is counted. Responses that 
             do not have a body (e.g. 304) are not counted."
        ::= { clusterHTTPStatsEntry 50 }

clusterHTTPStatsTargetBytesOutGIF OBJECT-TYPE
        SYNTAX     Counter64
        MAX-ACCESS read-only
        STATUS     current
        DESCRIPTION
            "Total number of HTTP response body bytes with the given content 
             type that are remaining AFTER the TX performs its HTTP-level 
             response body processing (excluding chunk headers).  HTTP response 
             headers and chunk headers/trailers are not counted, but any
             compressed or uncompressed HTTP response data is counted.
             Responses that do not have a body (e.g. 304) are not counted."
        ::= { clusterHTTPStatsEntry 51 }

clusterHTTPStatsTargetBytesOutJPEG OBJECT-TYPE
        SYNTAX     Counter64
        MAX-ACCESS read-only
        STATUS     current
        DESCRIPTION
            "Total number of HTTP response body bytes with the given content 
             type that are remaining AFTER the TX performs its HTTP-level 
             response body processing (excluding chunk headers).  HTTP response 
             headers and chunk headers/trailers are not counted, but any
             compressed or uncompressed HTTP response data is counted.
             Responses that do not have a body (e.g. 304) are not counted."
        ::= { clusterHTTPStatsEntry 52 }

clusterHTTPStatsTargetBytesOutHTML OBJECT-TYPE
        SYNTAX     Counter64
        MAX-ACCESS read-only
        STATUS     current
        DESCRIPTION
            "Total number of HTTP response body bytes with the given content 
             type that are remaining AFTER the TX performs its HTTP-level 
             response body processing (excluding chunk headers).  HTTP response 
             headers and chunk headers/trailers are not counted, but any
             compressed or uncompressed HTTP response data is counted.
             Responses that do not have a body (e.g. 304) are not counted."
        ::= { clusterHTTPStatsEntry 53 }

clusterHTTPStatsTargetBytesOutCSS OBJECT-TYPE
        SYNTAX     Counter64
        MAX-ACCESS read-only
        STATUS     current
        DESCRIPTION
            "Total number of HTTP response body bytes with the given content 
             type that are remaining AFTER the TX performs its HTTP-level 
             response body processing (excluding chunk headers).  HTTP response 
             headers and chunk headers/trailers are not counted, but any
             compressed or uncompressed HTTP response data is counted.
             Responses that do not have a body (e.g. 304) are not counted."
        ::= { clusterHTTPStatsEntry 54 }

clusterHTTPStatsTargetBytesOutXML OBJECT-TYPE
        SYNTAX     Counter64
        MAX-ACCESS read-only
        STATUS     current
        DESCRIPTION
            "Total number of HTTP response body bytes with the given content 
             type that are remaining AFTER the TX performs its HTTP-level 
             response body processing (excluding chunk headers).  HTTP response 
             headers and chunk headers/trailers are not counted, but any
             compressed or uncompressed HTTP response data is counted.
             Responses that do not have a body (e.g. 304) are not counted."
        ::= { clusterHTTPStatsEntry 55 }

clusterHTTPStatsTargetBytesOutTEXT OBJECT-TYPE
        SYNTAX     Counter64
        MAX-ACCESS read-only
        STATUS     current
        DESCRIPTION
            "Total number of HTTP response body bytes with the given content 
             type that are remaining AFTER the TX performs its HTTP-level 
             response body processing (excluding chunk headers).  HTTP response 
             headers and chunk headers/trailers are not counted, but any
             compressed or uncompressed HTTP response data is counted.
             Responses that do not have a body (e.g. 304) are not counted."
        ::= { clusterHTTPStatsEntry 56 }

clusterHTTPStatsTargetBytesOutJAVASCRIPT OBJECT-TYPE
        SYNTAX     Counter64
        MAX-ACCESS read-only
        STATUS     current
        DESCRIPTION
            "Total number of HTTP response body bytes with the given content 
             type that are remaining AFTER the TX performs its HTTP-level 
             response body processing (excluding chunk headers).  HTTP response 
             headers and chunk headers/trailers are not counted, but any
             compressed or uncompressed HTTP response data is counted.
             Responses that do not have a body (e.g. 304) are not counted."
        ::= { clusterHTTPStatsEntry 57 }

clusterHTTPStatsTargetBytesOutFLASH OBJECT-TYPE
        SYNTAX     Counter64
        MAX-ACCESS read-only
        STATUS     current
        DESCRIPTION
            "Total number of HTTP response body bytes with the given content 
             type that are remaining AFTER the TX performs its HTTP-level 
             response body processing (excluding chunk headers).  HTTP response 
             headers and chunk headers/trailers are not counted, but any
             compressed or uncompressed HTTP response data is counted.
             Responses that do not have a body (e.g. 304) are not counted."
        ::= { clusterHTTPStatsEntry 58 }

clusterHTTPStatsTargetBytesOutOthers OBJECT-TYPE
        SYNTAX     Counter64
        MAX-ACCESS read-only
        STATUS     current
        DESCRIPTION
            "Total number of HTTP response body bytes with the given content 
             type that are remaining AFTER the TX performs its HTTP-level 
             response body processing (excluding chunk headers).  HTTP response 
             headers and chunk headers/trailers are not counted, but any
             compressed or uncompressed HTTP response data is counted.
             Responses that do not have a body (e.g. 304) are not counted."
        ::= { clusterHTTPStatsEntry 59 }

clusterHTTPStatsListenBrowserIE51 OBJECT-TYPE
        SYNTAX     Counter64
        MAX-ACCESS read-only
        STATUS     current
        DESCRIPTION
            "The number of client requests from browser IE 5.1."
        ::= { clusterHTTPStatsEntry 60 }

clusterHTTPStatsListenBrowserNetscape6 OBJECT-TYPE
        SYNTAX     Counter64
        MAX-ACCESS read-only
        STATUS     current
        DESCRIPTION
            "The number of client requests from browser Netscape 6."
        ::= { clusterHTTPStatsEntry 61 }

clusterHTTPStatsListenBrowserMozilla OBJECT-TYPE
        SYNTAX     Counter64
        MAX-ACCESS read-only
        STATUS     current
        DESCRIPTION
            "The number of client requests from browser Mozilla."
        ::= { clusterHTTPStatsEntry 62 }

clusterHTTPStatsListenBrowserKonquerer OBJECT-TYPE
        SYNTAX     Counter64
        MAX-ACCESS read-only
        STATUS     current
        DESCRIPTION
            "The number of client requests from browser Konquerer."
        ::= { clusterHTTPStatsEntry 63 }

clusterHTTPStatsListenBrowserSafari OBJECT-TYPE
        SYNTAX     Counter64
        MAX-ACCESS read-only
        STATUS     current
        DESCRIPTION
            "The number of client requests from browser Safari."
        ::= { clusterHTTPStatsEntry 64 }

clusterHTTPStatsListenBrowserNone OBJECT-TYPE
        SYNTAX     Counter64
        MAX-ACCESS read-only
        STATUS     current
        DESCRIPTION
            "The number of client requests with no browser specified."
        ::= { clusterHTTPStatsEntry 65 }

clusterHTTPStatsListenPUTReq OBJECT-TYPE
        SYNTAX     Counter64
        MAX-ACCESS read-only
        STATUS     current
        DESCRIPTION
            "The total number of PUT HTTP requests."
        ::= { clusterHTTPStatsEntry 66 }

clusterHTTPStatsListenDELETEReq OBJECT-TYPE
        SYNTAX     Counter64
        MAX-ACCESS read-only
        STATUS     current
        DESCRIPTION
            "The total number of DELETE HTTP requests."
        ::= { clusterHTTPStatsEntry 67 }

clusterHTTPStatsListenTRACEReq OBJECT-TYPE
        SYNTAX     Counter64
        MAX-ACCESS read-only
        STATUS     current
        DESCRIPTION
            "The total number of TRACE HTTP requests."
        ::= { clusterHTTPStatsEntry 68 }

clusterHTTPStatsListenOPTIONSReq OBJECT-TYPE
        SYNTAX     Counter64
        MAX-ACCESS read-only
        STATUS     current
        DESCRIPTION
            "The total number of OPTIONS HTTP requests."
        ::= { clusterHTTPStatsEntry 69 }

clusterHTTPStatsListenCONNECTReq OBJECT-TYPE
        SYNTAX     Counter64
        MAX-ACCESS read-only
        STATUS     current
        DESCRIPTION
            "The total number of CONNECT HTTP requests."
        ::= { clusterHTTPStatsEntry 70 }

clusterHTTPStatsListenPROPFINDReq OBJECT-TYPE
        SYNTAX     Counter64
        MAX-ACCESS read-only
        STATUS     current
        DESCRIPTION
            "The total number of PROPFIND HTTP requests."
        ::= { clusterHTTPStatsEntry 71 }

clusterHTTPStatsListenPROPPATCHReq OBJECT-TYPE
        SYNTAX     Counter64
        MAX-ACCESS read-only
        STATUS     current
        DESCRIPTION
            "The total number of PROPPATCH HTTP requests."
        ::= { clusterHTTPStatsEntry 72 }

clusterHTTPStatsListenMKCOLReq OBJECT-TYPE
        SYNTAX     Counter64
        MAX-ACCESS read-only
        STATUS     current
        DESCRIPTION
            "The total number of MKCOL HTTP requests."
        ::= { clusterHTTPStatsEntry 73 }

clusterHTTPStatsListenCOPYReq OBJECT-TYPE
        SYNTAX     Counter64
        MAX-ACCESS read-only
        STATUS     current
        DESCRIPTION
            "The total number of COPY HTTP requests."
        ::= { clusterHTTPStatsEntry 74 }

clusterHTTPStatsListenMOVEReq OBJECT-TYPE
        SYNTAX     Counter64
        MAX-ACCESS read-only
        STATUS     current
        DESCRIPTION
            "The total number of MOVE HTTP requests."
        ::= { clusterHTTPStatsEntry 75 }

clusterHTTPStatsListenLOCKReq OBJECT-TYPE
        SYNTAX     Counter64
        MAX-ACCESS read-only
        STATUS     current
        DESCRIPTION
            "The total number of LOCK HTTP requests."
        ::= { clusterHTTPStatsEntry 76 }

clusterHTTPStatsListenUNLOCKReq OBJECT-TYPE
        SYNTAX     Counter64
        MAX-ACCESS read-only
        STATUS     current
        DESCRIPTION
            "The total number of UNLOCK HTTP requests."
        ::= { clusterHTTPStatsEntry 77 }

clusterHTTPStatsListenBCOPYReq OBJECT-TYPE
        SYNTAX     Counter64
        MAX-ACCESS read-only
        STATUS     current
        DESCRIPTION
            "The total number of BCOPY HTTP requests."
        ::= { clusterHTTPStatsEntry 78 }

clusterHTTPStatsListenBDELETEReq OBJECT-TYPE
        SYNTAX     Counter64
        MAX-ACCESS read-only
        STATUS     current
        DESCRIPTION
            "The total number of BDELETE HTTP requests."
        ::= { clusterHTTPStatsEntry 79 }

clusterHTTPStatsListenBMOVEReq OBJECT-TYPE
        SYNTAX     Counter64
        MAX-ACCESS read-only
        STATUS     current
        DESCRIPTION
            "The total number of BMOVE HTTP requests."
        ::= { clusterHTTPStatsEntry 80 }

clusterHTTPStatsListenBPROPFINDReq OBJECT-TYPE
        SYNTAX     Counter64
        MAX-ACCESS read-only
        STATUS     current
        DESCRIPTION
            "The total number of BPROPFIND HTTP requests."
        ::= { clusterHTTPStatsEntry 81 }

clusterHTTPStatsListenBPROPPATCHReq OBJECT-TYPE
        SYNTAX     Counter64
        MAX-ACCESS read-only
        STATUS     current
        DESCRIPTION
            "The total number of BPROPPATCH HTTP requests."
        ::= { clusterHTTPStatsEntry 82 }

clusterHTTPStatsListenNOTIFYReq OBJECT-TYPE
        SYNTAX     Counter64
        MAX-ACCESS read-only
        STATUS     current
        DESCRIPTION
            "The total number of NOTIFY HTTP requests."
        ::= { clusterHTTPStatsEntry 83 }

clusterHTTPStatsListenPOLLReq OBJECT-TYPE
        SYNTAX     Counter64
        MAX-ACCESS read-only
        STATUS     current
        DESCRIPTION
            "The total number of POLL HTTP requests."
        ::= { clusterHTTPStatsEntry 84 }

clusterHTTPStatsListenSEARCHReq OBJECT-TYPE
        SYNTAX     Counter64
        MAX-ACCESS read-only
        STATUS     current
        DESCRIPTION
            "The total number of SEARCH HTTP requests."
        ::= { clusterHTTPStatsEntry 85 }

clusterHTTPStatsListenSUBSCRIBEReq OBJECT-TYPE
        SYNTAX     Counter64
        MAX-ACCESS read-only
        STATUS     current
        DESCRIPTION
            "The total number of SUBSCRIBE HTTP requests."
        ::= { clusterHTTPStatsEntry 86 }

clusterHTTPStatsListenUNSUBSCRIBEReq OBJECT-TYPE
        SYNTAX     Counter64
        MAX-ACCESS read-only
        STATUS     current
        DESCRIPTION
            "The total number of UNSUBSCRIBE HTTP requests."
        ::= { clusterHTTPStatsEntry 87 }

clusterHTTPStatsListenXMSENUMATTSReq OBJECT-TYPE
        SYNTAX     Counter64
        MAX-ACCESS read-only
        STATUS     current
        DESCRIPTION
            "The total number of XMSENUMATTS HTTP requests."
        ::= { clusterHTTPStatsEntry 88 }

clusterHTTPStatsListenVERSIONCONTROLReq OBJECT-TYPE
        SYNTAX     Counter64
        MAX-ACCESS read-only
        STATUS     current
        DESCRIPTION
            "The total number of VERSIONCONTROL HTTP requests."
        ::= { clusterHTTPStatsEntry 89 }

clusterHTTPStatsListenREPORTReq OBJECT-TYPE
        SYNTAX     Counter64
        MAX-ACCESS read-only
        STATUS     current
        DESCRIPTION
            "The total number of REPORT HTTP requests."
        ::= { clusterHTTPStatsEntry 90 }

clusterHTTPStatsListenCHECKOUTReq OBJECT-TYPE
        SYNTAX     Counter64
        MAX-ACCESS read-only
        STATUS     current
        DESCRIPTION
            "The total number of CHECKOUT HTTP requests."
        ::= { clusterHTTPStatsEntry 91 }

clusterHTTPStatsListenCHECKINReq OBJECT-TYPE
        SYNTAX     Counter64
        MAX-ACCESS read-only
        STATUS     current
        DESCRIPTION
            "The total number of CHECKIN HTTP requests."
        ::= { clusterHTTPStatsEntry 92 }

clusterHTTPStatsListenUNCHECKOUTReq OBJECT-TYPE
        SYNTAX     Counter64
        MAX-ACCESS read-only
        STATUS     current
        DESCRIPTION
            "The total number of UNCHECKOUT HTTP requests."
        ::= { clusterHTTPStatsEntry 93 }

clusterHTTPStatsListenMKWORKSPACEReq OBJECT-TYPE
        SYNTAX     Counter64
        MAX-ACCESS read-only
        STATUS     current
        DESCRIPTION
            "The total number of MKWORKSPACE HTTP requests."
        ::= { clusterHTTPStatsEntry 94 }

clusterHTTPStatsListenUPDATEReq OBJECT-TYPE
        SYNTAX     Counter64
        MAX-ACCESS read-only
        STATUS     current
        DESCRIPTION
            "The total number of UPDATE HTTP requests."
        ::= { clusterHTTPStatsEntry 95 }

clusterHTTPStatsListenLABELReq OBJECT-TYPE
        SYNTAX     Counter64
        MAX-ACCESS read-only
        STATUS     current
        DESCRIPTION
            "The total number of LABEL HTTP requests."
        ::= { clusterHTTPStatsEntry 96 }

clusterHTTPStatsListenMERGEReq OBJECT-TYPE
        SYNTAX     Counter64
        MAX-ACCESS read-only
        STATUS     current
        DESCRIPTION
            "The total number of MERGE HTTP requests."
        ::= { clusterHTTPStatsEntry 97 }

clusterHTTPStatsListenBASELINECONTROLReq OBJECT-TYPE
        SYNTAX     Counter64
        MAX-ACCESS read-only
        STATUS     current
        DESCRIPTION
            "The total number of BASELINECONTROL HTTP requests."
        ::= { clusterHTTPStatsEntry 98 }

clusterHTTPStatsListenMKACTIVITYReq OBJECT-TYPE
        SYNTAX     Counter64
        MAX-ACCESS read-only
        STATUS     current
        DESCRIPTION
            "The total number of MKACTIVITY HTTP requests."
        ::= { clusterHTTPStatsEntry 99 }

clusterHTTPStatsListenBINDReq OBJECT-TYPE
        SYNTAX     Counter64
        MAX-ACCESS read-only
        STATUS     current
        DESCRIPTION
            "The total number of BIND HTTP requests."
        ::= { clusterHTTPStatsEntry 100 }

clusterHTTPStatsListenMKRESOURCEReq OBJECT-TYPE
        SYNTAX     Counter64
        MAX-ACCESS read-only
        STATUS     current
        DESCRIPTION
            "The total number of MKRESOURCE HTTP requests."
        ::= { clusterHTTPStatsEntry 101 }

clusterHTTPStatsListenORDERPATCHReq OBJECT-TYPE
        SYNTAX     Counter64
        MAX-ACCESS read-only
        STATUS     current
        DESCRIPTION
            "The total number of ORDERPATH HTTP requests."
        ::= { clusterHTTPStatsEntry 102 }

clusterHTTPStatsListenACLReq OBJECT-TYPE
        SYNTAX     Counter64
        MAX-ACCESS read-only
        STATUS     current
        DESCRIPTION
            "The total number of ACL HTTP requests."
        ::= { clusterHTTPStatsEntry 103 }

clusterHTTPStatsTargetResponseCode1xx OBJECT-TYPE
        SYNTAX     Counter64
        MAX-ACCESS read-only
        STATUS     current
        DESCRIPTION
            "The total number of HTTP 1xx response code."
        ::= { clusterHTTPStatsEntry 104 }

clusterHTTPStatsTargetResponseCode101 OBJECT-TYPE
        SYNTAX     Counter64
        MAX-ACCESS read-only
        STATUS     current
        DESCRIPTION
            "The total number of HTTP 101 response code."
        ::= { clusterHTTPStatsEntry 105 }

clusterHTTPStatsTargetResponseCode102 OBJECT-TYPE
        SYNTAX     Counter64
        MAX-ACCESS read-only
        STATUS     current
        DESCRIPTION
            "The total number of HTTP 102 response code."
        ::= { clusterHTTPStatsEntry 106 }

clusterHTTPStatsTargetResponseCode2xx OBJECT-TYPE
        SYNTAX     Counter64
        MAX-ACCESS read-only
        STATUS     current
        DESCRIPTION
            "The total number of HTTP 2xx response code."
        ::= { clusterHTTPStatsEntry 107 }

clusterHTTPStatsTargetResponseCode201 OBJECT-TYPE
        SYNTAX     Counter64
        MAX-ACCESS read-only
        STATUS     current
        DESCRIPTION
            "The total number of HTTP 201 response code."
        ::= { clusterHTTPStatsEntry 108 }

clusterHTTPStatsTargetResponseCode202 OBJECT-TYPE
        SYNTAX     Counter64
        MAX-ACCESS read-only
        STATUS     current
        DESCRIPTION
            "The total number of HTTP 202 response code."
        ::= { clusterHTTPStatsEntry 109 }

clusterHTTPStatsTargetResponseCode203 OBJECT-TYPE
        SYNTAX     Counter64
        MAX-ACCESS read-only
        STATUS     current
        DESCRIPTION
            "The total number of HTTP 203 response code."
        ::= { clusterHTTPStatsEntry 110 }

clusterHTTPStatsTargetResponseCode204 OBJECT-TYPE
        SYNTAX     Counter64
        MAX-ACCESS read-only
        STATUS     current
        DESCRIPTION
            "The total number of HTTP 204 response code."
        ::= { clusterHTTPStatsEntry 111 }

clusterHTTPStatsTargetResponseCode205 OBJECT-TYPE
        SYNTAX     Counter64
        MAX-ACCESS read-only
        STATUS     current
        DESCRIPTION
            "The total number of HTTP 205 response code."
        ::= { clusterHTTPStatsEntry 112 }

clusterHTTPStatsTargetResponseCode206 OBJECT-TYPE
        SYNTAX     Counter64
        MAX-ACCESS read-only
        STATUS     current
        DESCRIPTION
            "The total number of HTTP 206 response code."
        ::= { clusterHTTPStatsEntry 113 }

clusterHTTPStatsTargetResponseCode207 OBJECT-TYPE
        SYNTAX     Counter64
        MAX-ACCESS read-only
        STATUS     current
        DESCRIPTION
            "The total number of HTTP 207 response code."
        ::= { clusterHTTPStatsEntry 114 }

clusterHTTPStatsTargetResponseCode300 OBJECT-TYPE
        SYNTAX     Counter64
        MAX-ACCESS read-only
        STATUS     current
        DESCRIPTION
            "The total number of HTTP 300 response code."
        ::= { clusterHTTPStatsEntry 115 }

clusterHTTPStatsTargetResponseCode301 OBJECT-TYPE
        SYNTAX     Counter64
        MAX-ACCESS read-only
        STATUS     current
        DESCRIPTION
            "The total number of HTTP 301 response code."
        ::= { clusterHTTPStatsEntry 116 }

clusterHTTPStatsTargetResponseCode303 OBJECT-TYPE
        SYNTAX     Counter64
        MAX-ACCESS read-only
        STATUS     current
        DESCRIPTION
            "The total number of HTTP 303 response code."
        ::= { clusterHTTPStatsEntry 117 }

clusterHTTPStatsTargetResponseCode305 OBJECT-TYPE
        SYNTAX     Counter64
        MAX-ACCESS read-only
        STATUS     current
        DESCRIPTION
            "The total number of HTTP 305 response code."
        ::= { clusterHTTPStatsEntry 118 }

clusterHTTPStatsTargetResponseCode306 OBJECT-TYPE
        SYNTAX     Counter64
        MAX-ACCESS read-only
        STATUS     current
        DESCRIPTION
            "The total number of HTTP 300 response code."
        ::= { clusterHTTPStatsEntry 119 }

clusterHTTPStatsTargetResponseCode307 OBJECT-TYPE
        SYNTAX     Counter64
        MAX-ACCESS read-only
        STATUS     current
        DESCRIPTION
            "The total number of HTTP 307 response code."
        ::= { clusterHTTPStatsEntry 120 }

clusterHTTPStatsTargetResponseCode400 OBJECT-TYPE
        SYNTAX     Counter64
        MAX-ACCESS read-only
        STATUS     current
        DESCRIPTION
            "The total number of HTTP 400 response code."
        ::= { clusterHTTPStatsEntry 121 }

clusterHTTPStatsTargetResponseCode401 OBJECT-TYPE
        SYNTAX     Counter64
        MAX-ACCESS read-only
        STATUS     current
        DESCRIPTION
            "The total number of HTTP 401 response code."
        ::= { clusterHTTPStatsEntry 122 }

clusterHTTPStatsTargetResponseCode402 OBJECT-TYPE
        SYNTAX     Counter64
        MAX-ACCESS read-only
        STATUS     current
        DESCRIPTION
            "The total number of HTTP 402 response code."
        ::= { clusterHTTPStatsEntry 123 }

clusterHTTPStatsTargetResponseCode403 OBJECT-TYPE
        SYNTAX     Counter64
        MAX-ACCESS read-only
        STATUS     current
        DESCRIPTION
            "The total number of HTTP 403 response code."
        ::= { clusterHTTPStatsEntry 124 }

clusterHTTPStatsTargetResponseCode405 OBJECT-TYPE
        SYNTAX     Counter64
        MAX-ACCESS read-only
        STATUS     current
        DESCRIPTION
            "The total number of HTTP 405 response code."
        ::= { clusterHTTPStatsEntry 125 }

clusterHTTPStatsTargetResponseCode406 OBJECT-TYPE
        SYNTAX     Counter64
        MAX-ACCESS read-only
        STATUS     current
        DESCRIPTION
            "The total number of HTTP 406 response code."
        ::= { clusterHTTPStatsEntry 126 }

clusterHTTPStatsTargetResponseCode407 OBJECT-TYPE
        SYNTAX     Counter64
        MAX-ACCESS read-only
        STATUS     current
        DESCRIPTION
            "The total number of HTTP 407 response code."
        ::= { clusterHTTPStatsEntry 127 }

clusterHTTPStatsTargetResponseCode408 OBJECT-TYPE
        SYNTAX     Counter64
        MAX-ACCESS read-only
        STATUS     current
        DESCRIPTION
            "The total number of HTTP 408 response code."
        ::= { clusterHTTPStatsEntry 128 }

clusterHTTPStatsTargetResponseCode409 OBJECT-TYPE
        SYNTAX     Counter64
        MAX-ACCESS read-only
        STATUS     current
        DESCRIPTION
            "The total number of HTTP 409 response code."
        ::= { clusterHTTPStatsEntry 129 }

clusterHTTPStatsTargetResponseCode410 OBJECT-TYPE
        SYNTAX     Counter64
        MAX-ACCESS read-only
        STATUS     current
        DESCRIPTION
            "The total number of HTTP 410 response code."
        ::= { clusterHTTPStatsEntry 130 }

clusterHTTPStatsTargetResponseCode411 OBJECT-TYPE
        SYNTAX     Counter64
        MAX-ACCESS read-only
        STATUS     current
        DESCRIPTION
            "The total number of HTTP 411 response code."
        ::= { clusterHTTPStatsEntry 131 }

clusterHTTPStatsTargetResponseCode412 OBJECT-TYPE
        SYNTAX     Counter64
        MAX-ACCESS read-only
        STATUS     current
        DESCRIPTION
            "The total number of HTTP 412 response code."
        ::= { clusterHTTPStatsEntry 132 }

clusterHTTPStatsTargetResponseCode413 OBJECT-TYPE
        SYNTAX     Counter64
        MAX-ACCESS read-only
        STATUS     current
        DESCRIPTION
            "The total number of HTTP 413 response code."
        ::= { clusterHTTPStatsEntry 133 }

clusterHTTPStatsTargetResponseCode414 OBJECT-TYPE
        SYNTAX     Counter64
        MAX-ACCESS read-only
        STATUS     current
        DESCRIPTION
            "The total number of HTTP 414 response code."
        ::= { clusterHTTPStatsEntry 134 }

clusterHTTPStatsTargetResponseCode415 OBJECT-TYPE
        SYNTAX     Counter64
        MAX-ACCESS read-only
        STATUS     current
        DESCRIPTION
            "The total number of HTTP 415 response code."
        ::= { clusterHTTPStatsEntry 135 }

clusterHTTPStatsTargetResponseCode416 OBJECT-TYPE
        SYNTAX     Counter64
        MAX-ACCESS read-only
        STATUS     current
        DESCRIPTION
            "The total number of HTTP 416 response code."
        ::= { clusterHTTPStatsEntry 136 }

clusterHTTPStatsTargetResponseCode417 OBJECT-TYPE
        SYNTAX     Counter64
        MAX-ACCESS read-only
        STATUS     current
        DESCRIPTION
            "The total number of HTTP 417 response code."
        ::= { clusterHTTPStatsEntry 137 }

clusterHTTPStatsTargetResponseCode422 OBJECT-TYPE
        SYNTAX     Counter64
        MAX-ACCESS read-only
        STATUS     current
        DESCRIPTION
            "The total number of HTTP 422 response code."
        ::= { clusterHTTPStatsEntry 138 }

clusterHTTPStatsTargetResponseCode423 OBJECT-TYPE
        SYNTAX     Counter64
        MAX-ACCESS read-only
        STATUS     current
        DESCRIPTION
            "The total number of HTTP 423 response code."
        ::= { clusterHTTPStatsEntry 139 }

clusterHTTPStatsTargetResponseCode424 OBJECT-TYPE
        SYNTAX     Counter64
        MAX-ACCESS read-only
        STATUS     current
        DESCRIPTION
            "The total number of HTTP 424 response code."
        ::= { clusterHTTPStatsEntry 140 }

clusterHTTPStatsTargetResponseCode425 OBJECT-TYPE
        SYNTAX     Counter64
        MAX-ACCESS read-only
        STATUS     current
        DESCRIPTION
            "The total number of HTTP 425 response code."
        ::= { clusterHTTPStatsEntry 141 }

clusterHTTPStatsTargetResponseCode500 OBJECT-TYPE
        SYNTAX     Counter64
        MAX-ACCESS read-only
        STATUS     current
        DESCRIPTION
            "The total number of HTTP 500 response code."
        ::= { clusterHTTPStatsEntry 142 }

clusterHTTPStatsTargetResponseCode501 OBJECT-TYPE
        SYNTAX     Counter64
        MAX-ACCESS read-only
        STATUS     current
        DESCRIPTION
            "The total number of HTTP 501 response code."
        ::= { clusterHTTPStatsEntry 143 }

clusterHTTPStatsTargetResponseCode502 OBJECT-TYPE
        SYNTAX     Counter64
        MAX-ACCESS read-only
        STATUS     current
        DESCRIPTION
            "The total number of HTTP 502 response code."
        ::= { clusterHTTPStatsEntry 144 }

clusterHTTPStatsTargetResponseCode503 OBJECT-TYPE
        SYNTAX     Counter64
        MAX-ACCESS read-only
        STATUS     current
        DESCRIPTION
            "The total number of HTTP 503 response code."
        ::= { clusterHTTPStatsEntry 145 }

clusterHTTPStatsTargetResponseCode504 OBJECT-TYPE
        SYNTAX     Counter64
        MAX-ACCESS read-only
        STATUS     current
        DESCRIPTION
            "The total number of HTTP 504 response code."
        ::= { clusterHTTPStatsEntry 146 }

clusterHTTPStatsTargetResponseCode505 OBJECT-TYPE
        SYNTAX     Counter64
        MAX-ACCESS read-only
        STATUS     current
        DESCRIPTION
            "The total number of HTTP 505 response code."
        ::= { clusterHTTPStatsEntry 147 }

clusterHTTPStatsTargetResponseCode506 OBJECT-TYPE
        SYNTAX     Counter64
        MAX-ACCESS read-only
        STATUS     current
        DESCRIPTION
            "The total number of HTTP 506 response code."
        ::= { clusterHTTPStatsEntry 148 }

clusterHTTPStatsTargetResponseCode507 OBJECT-TYPE
        SYNTAX     Counter64
        MAX-ACCESS read-only
        STATUS     current
        DESCRIPTION
            "The total number of HTTP 507 response code."
        ::= { clusterHTTPStatsEntry 149 }

clusterHTTPStatsTargetContentXCOMPONENT OBJECT-TYPE
        SYNTAX     Counter64
        MAX-ACCESS read-only
        STATUS     current
        DESCRIPTION
            "The total number of responses with content type X-COMPONENT."
        ::= { clusterHTTPStatsEntry 150 }

clusterHTTPStatsTargetContentOCTETSTREAM OBJECT-TYPE
        SYNTAX     Counter64
        MAX-ACCESS read-only
        STATUS     current
        DESCRIPTION
            "The total number of responses with content type OCTET-STREAM."
        ::= { clusterHTTPStatsEntry 151 }

clusterHTTPStatsTargetContentMSWORD OBJECT-TYPE
        SYNTAX     Counter64
        MAX-ACCESS read-only
        STATUS     current
        DESCRIPTION
            "The total number of responses with content type MSWORD."
        ::= { clusterHTTPStatsEntry 152 }

clusterHTTPStatsTargetContentMSEXCEL OBJECT-TYPE
        SYNTAX     Counter64
        MAX-ACCESS read-only
        STATUS     current
        DESCRIPTION
            "The total number of responses with content type MSEXCEL."
        ::= { clusterHTTPStatsEntry 153 }

clusterHTTPStatsTargetContentMSPOWERPOINT OBJECT-TYPE
        SYNTAX     Counter64
        MAX-ACCESS read-only
        STATUS     current
        DESCRIPTION
            "The total number of responses with content type MSPOWERPOINT."
        ::= { clusterHTTPStatsEntry 154 }

clusterHTTPStatsTargetContentCUSTOM1 OBJECT-TYPE
        SYNTAX     Counter64
        MAX-ACCESS read-only
        STATUS     current
        DESCRIPTION
            "The total number of responses with content type CUSTOM1."
        ::= { clusterHTTPStatsEntry 155 }

clusterHTTPStatsTargetContentCUSTOM2 OBJECT-TYPE
        SYNTAX     Counter64
        MAX-ACCESS read-only
        STATUS     current
        DESCRIPTION
            "The total number of responses with content type CUSTOM2."
        ::= { clusterHTTPStatsEntry 156 }

clusterHTTPStatsTargetContentCUSTOM3 OBJECT-TYPE
        SYNTAX     Counter64
        MAX-ACCESS read-only
        STATUS     current
        DESCRIPTION
            "The total number of responses with content type CUSTOM3."
        ::= { clusterHTTPStatsEntry 157 }

clusterHTTPStatsTargetBytesInXCOMPONENT OBJECT-TYPE
        SYNTAX     Counter64
        MAX-ACCESS read-only
        STATUS     current
        DESCRIPTION
            "Total number of HTTP response body bytes received with the 
             given content type (excluding chunk headers) BEFORE the TX 
             performs its HTTP-level response body processing. HTTP response 
             headers and chunk headers/trailers are not counted, but any 
             compressed or uncompressed HTTP data is counted. Responses that 
             do not have a body (e.g. 304) are not counted."
        ::= { clusterHTTPStatsEntry 158 }

clusterHTTPStatsTargetBytesInOCTETSTREAM OBJECT-TYPE
        SYNTAX     Counter64
        MAX-ACCESS read-only
        STATUS     current
        DESCRIPTION
            "Total number of HTTP response body bytes received with the 
             given content type (excluding chunk headers) BEFORE the TX 
             performs its HTTP-level response body processing. HTTP response 
             headers and chunk headers/trailers are not counted, but any 
             compressed or uncompressed HTTP data is counted. Responses that 
             do not have a body (e.g. 304) are not counted."
        ::= { clusterHTTPStatsEntry 159 }

clusterHTTPStatsTargetBytesInMSWORD OBJECT-TYPE
        SYNTAX     Counter64
        MAX-ACCESS read-only
        STATUS     current
        DESCRIPTION
            "Total number of HTTP response body bytes received with the 
             given content type (excluding chunk headers) BEFORE the TX 
             performs its HTTP-level response body processing. HTTP response 
             headers and chunk headers/trailers are not counted, but any 
             compressed or uncompressed HTTP data is counted. Responses that 
             do not have a body (e.g. 304) are not counted."
        ::= { clusterHTTPStatsEntry 160 }

clusterHTTPStatsTargetBytesInMSEXCEL OBJECT-TYPE
        SYNTAX     Counter64
        MAX-ACCESS read-only
        STATUS     current
        DESCRIPTION
            "Total number of HTTP response body bytes received with the 
             given content type (excluding chunk headers) BEFORE the TX 
             performs its HTTP-level response body processing. HTTP response 
             headers and chunk headers/trailers are not counted, but any 
             compressed or uncompressed HTTP data is counted. Responses that 
             do not have a body (e.g. 304) are not counted."
        ::= { clusterHTTPStatsEntry 161 }

clusterHTTPStatsTargetBytesInMSPOWERPOINT OBJECT-TYPE
        SYNTAX     Counter64
        MAX-ACCESS read-only
        STATUS     current
        DESCRIPTION
            "Total number of HTTP response body bytes received with the 
             given content type (excluding chunk headers) BEFORE the TX 
             performs its HTTP-level response body processing. HTTP response 
             headers and chunk headers/trailers are not counted, but any 
             compressed or uncompressed HTTP data is counted. Responses that 
             do not have a body (e.g. 304) are not counted."
        ::= { clusterHTTPStatsEntry 162 }

clusterHTTPStatsTargetBytesInCUSTOM1 OBJECT-TYPE
        SYNTAX     Counter64
        MAX-ACCESS read-only
        STATUS     current
        DESCRIPTION
            "Total number of HTTP response body bytes received with the 
             given content type (excluding chunk headers) BEFORE the TX 
             performs its HTTP-level response body processing. HTTP response 
             headers and chunk headers/trailers are not counted, but any 
             compressed or uncompressed HTTP data is counted. Responses that 
             do not have a body (e.g. 304) are not counted."
        ::= { clusterHTTPStatsEntry 163 }

clusterHTTPStatsTargetBytesInCUSTOM2 OBJECT-TYPE
        SYNTAX     Counter64
        MAX-ACCESS read-only
        STATUS     current
        DESCRIPTION
            "Total number of HTTP response body bytes received with the 
             given content type (excluding chunk headers) BEFORE the TX 
             performs its HTTP-level response body processing. HTTP response 
             headers and chunk headers/trailers are not counted, but any 
             compressed or uncompressed HTTP data is counted. Responses that 
             do not have a body (e.g. 304) are not counted."
        ::= { clusterHTTPStatsEntry 164 }

clusterHTTPStatsTargetBytesInCUSTOM3 OBJECT-TYPE
        SYNTAX     Counter64
        MAX-ACCESS read-only
        STATUS     current
        DESCRIPTION
            "Total number of HTTP response body bytes received with the 
             given content type (excluding chunk headers) BEFORE the TX 
             performs its HTTP-level response body processing. HTTP response 
             headers and chunk headers/trailers are not counted, but any 
             compressed or uncompressed HTTP data is counted. Responses that 
             do not have a body (e.g. 304) are not counted."
        ::= { clusterHTTPStatsEntry 165 }

clusterHTTPStatsTargetBytesOutXCOMPONENT OBJECT-TYPE
        SYNTAX     Counter64
        MAX-ACCESS read-only
        STATUS     current
        DESCRIPTION
            "Total number of HTTP response body bytes with the given content 
             type that are remaining AFTER the TX performs its HTTP-level 
             response body processing (excluding chunk headers).  HTTP response 
             headers and chunk headers/trailers are not counted, but any
             compressed or uncompressed HTTP response data is counted.
             Responses that do not have a body (e.g. 304) are not counted."
        ::= { clusterHTTPStatsEntry 166 }

clusterHTTPStatsTargetBytesOutOCTETSTREAM OBJECT-TYPE
        SYNTAX     Counter64
        MAX-ACCESS read-only
        STATUS     current
        DESCRIPTION
            "Total number of HTTP response body bytes with the given content 
             type that are remaining AFTER the TX performs its HTTP-level 
             response body processing (excluding chunk headers).  HTTP response 
             headers and chunk headers/trailers are not counted, but any
             compressed or uncompressed HTTP response data is counted.
             Responses that do not have a body (e.g. 304) are not counted."
        ::= { clusterHTTPStatsEntry 167 }

clusterHTTPStatsTargetBytesOutMSWORD OBJECT-TYPE
        SYNTAX     Counter64
        MAX-ACCESS read-only
        STATUS     current
        DESCRIPTION
            "Total number of HTTP response body bytes with the given content 
             type that are remaining AFTER the TX performs its HTTP-level 
             response body processing (excluding chunk headers).  HTTP response 
             headers and chunk headers/trailers are not counted, but any
             compressed or uncompressed HTTP response data is counted.
             Responses that do not have a body (e.g. 304) are not counted."
        ::= { clusterHTTPStatsEntry 168 }

clusterHTTPStatsTargetBytesOutMSEXCEL OBJECT-TYPE
        SYNTAX     Counter64
        MAX-ACCESS read-only
        STATUS     current
        DESCRIPTION
            "Total number of HTTP response body bytes with the given content 
             type that are remaining AFTER the TX performs its HTTP-level 
             response body processing (excluding chunk headers).  HTTP response 
             headers and chunk headers/trailers are not counted, but any
             compressed or uncompressed HTTP response data is counted.
             Responses that do not have a body (e.g. 304) are not counted."
        ::= { clusterHTTPStatsEntry 169 }

clusterHTTPStatsTargetBytesOutMSPOWERPOINT OBJECT-TYPE
        SYNTAX     Counter64
        MAX-ACCESS read-only
        STATUS     current
        DESCRIPTION
            "Total number of HTTP response body bytes with the given content 
             type that are remaining AFTER the TX performs its HTTP-level 
             response body processing (excluding chunk headers).  HTTP response 
             headers and chunk headers/trailers are not counted, but any
             compressed or uncompressed HTTP response data is counted.
             Responses that do not have a body (e.g. 304) are not counted."
        ::= { clusterHTTPStatsEntry 170 }

clusterHTTPStatsTargetBytesOutCUSTOM1 OBJECT-TYPE
        SYNTAX     Counter64
        MAX-ACCESS read-only
        STATUS     current
        DESCRIPTION
            "Total number of HTTP response body bytes with the given content 
             type that are remaining AFTER the TX performs its HTTP-level 
             response body processing (excluding chunk headers).  HTTP response 
             headers and chunk headers/trailers are not counted, but any
             compressed or uncompressed HTTP response data is counted.
             Responses that do not have a body (e.g. 304) are not counted."
        ::= { clusterHTTPStatsEntry 171 }

clusterHTTPStatsTargetBytesOutCUSTOM2 OBJECT-TYPE
        SYNTAX     Counter64
        MAX-ACCESS read-only
        STATUS     current
        DESCRIPTION
            "Total number of HTTP response body bytes with the given content 
             type that are remaining AFTER the TX performs its HTTP-level 
             response body processing (excluding chunk headers).  HTTP response 
             headers and chunk headers/trailers are not counted, but any
             compressed or uncompressed HTTP response data is counted.
             Responses that do not have a body (e.g. 304) are not counted."
        ::= { clusterHTTPStatsEntry 172 }

clusterHTTPStatsTargetBytesOutCUSTOM3 OBJECT-TYPE
        SYNTAX     Counter64
        MAX-ACCESS read-only
        STATUS     current
        DESCRIPTION
            "Total number of HTTP response body bytes with the given content 
             type that are remaining AFTER the TX performs its HTTP-level 
             response body processing (excluding chunk headers).  HTTP response 
             headers and chunk headers/trailers are not counted, but any
             compressed or uncompressed HTTP response data is counted.
             Responses that do not have a body (e.g. 304) are not counted."
        ::= { clusterHTTPStatsEntry 173 }

clusterHTTPStatsTargetDecompressionPerformed OBJECT-TYPE
        SYNTAX     Counter64
        MAX-ACCESS read-only
        STATUS     current
        DESCRIPTION
            "Number of times decompression performed by the server."
        ::= { clusterHTTPStatsEntry 174 }

clusterHTTPStatsTargetDecompressionFailure OBJECT-TYPE
        SYNTAX     Counter64
        MAX-ACCESS read-only
        STATUS     current
        DESCRIPTION
            "Number of failures when decompression was performed."
        ::= { clusterHTTPStatsEntry 175 }

clusterHTTPStatsTargetCompressContentGIF OBJECT-TYPE
        SYNTAX     Counter64
        MAX-ACCESS read-only
        STATUS     current
        DESCRIPTION
            "Number of compressed GIF objects sent to client."
        ::= { clusterHTTPStatsEntry 177 }

clusterHTTPStatsTargetCompressContentJPEG OBJECT-TYPE
        SYNTAX     Counter64
        MAX-ACCESS read-only
        STATUS     current
        DESCRIPTION
            "Number of compressed JPEF objects sent to client."
        ::= { clusterHTTPStatsEntry 178 }

clusterHTTPStatsTargetCompressContentHTML OBJECT-TYPE
        SYNTAX     Counter64
        MAX-ACCESS read-only
        STATUS     current
        DESCRIPTION
            "Number of compressed HTML objects sent to client."
        ::= { clusterHTTPStatsEntry 179 }

clusterHTTPStatsTargetCompressContentCSS OBJECT-TYPE
        SYNTAX     Counter64
        MAX-ACCESS read-only
        STATUS     current
        DESCRIPTION
            "Number of compressed CSS objects sent to client."
        ::= { clusterHTTPStatsEntry 180 }

clusterHTTPStatsTargetCompressContentXML OBJECT-TYPE
        SYNTAX     Counter64
        MAX-ACCESS read-only
        STATUS     current
        DESCRIPTION
            "Number of compressed XML objects sent to client."
        ::= { clusterHTTPStatsEntry 181 }

clusterHTTPStatsTargetCompressContentPLAIN OBJECT-TYPE
        SYNTAX     Counter64
        MAX-ACCESS read-only
        STATUS     current
        DESCRIPTION
            "Number of compressed PLAIN objects sent to client."
        ::= { clusterHTTPStatsEntry 182 }

clusterHTTPStatsTargetCompressContentXCOMPONENT OBJECT-TYPE
        SYNTAX     Counter64
        MAX-ACCESS read-only
        STATUS     current
        DESCRIPTION
            "Number of compressed X-COMPONENT objects sent to client."
        ::= { clusterHTTPStatsEntry 183 }

clusterHTTPStatsTargetCompressContentJAVASCRIPT OBJECT-TYPE
        SYNTAX     Counter64
        MAX-ACCESS read-only
        STATUS     current
        DESCRIPTION
            "Number of compressed JAVASCRIPT objects sent to client."
        ::= { clusterHTTPStatsEntry 184 }

clusterHTTPStatsTargetCompressContentFLASH OBJECT-TYPE
        SYNTAX     Counter64
        MAX-ACCESS read-only
        STATUS     current
        DESCRIPTION
            "Number of compressed FLASH objects sent to client."
        ::= { clusterHTTPStatsEntry 185 }

clusterHTTPStatsTargetCompressContentOCTETSTREAM OBJECT-TYPE
        SYNTAX     Counter64
        MAX-ACCESS read-only
        STATUS     current
        DESCRIPTION
            "Number of compressed OCTET-STREAM objects sent to client."
        ::= { clusterHTTPStatsEntry 186 }

clusterHTTPStatsTargetCompressContentMSWORD OBJECT-TYPE
        SYNTAX     Counter64
        MAX-ACCESS read-only
        STATUS     current
        DESCRIPTION
            "Number of compressed MS-WORD objects sent to client."
        ::= { clusterHTTPStatsEntry 187 }

clusterHTTPStatsTargetCompressContentMSEXCEL OBJECT-TYPE
        SYNTAX     Counter64
        MAX-ACCESS read-only
        STATUS     current
        DESCRIPTION
            "Number of compressed MS-EXCEL objects sent to client."
        ::= { clusterHTTPStatsEntry 188 }

clusterHTTPStatsTargetCompressContentMSPOWERPOINT OBJECT-TYPE
        SYNTAX     Counter64
        MAX-ACCESS read-only
        STATUS     current
        DESCRIPTION
            "Number of compressed MS-POWERPOINT objects sent to client."
        ::= { clusterHTTPStatsEntry 189 }

clusterHTTPStatsTargetCompressContentCUSTOM1 OBJECT-TYPE
        SYNTAX     Counter64
        MAX-ACCESS read-only
        STATUS     current
        DESCRIPTION
            "Number of compressed CUSTOM-1 objects sent to client."
        ::= { clusterHTTPStatsEntry 190 }

clusterHTTPStatsTargetCompressContentCUSTOM2 OBJECT-TYPE
        SYNTAX     Counter64
        MAX-ACCESS read-only
        STATUS     current
        DESCRIPTION
            "Number of compressed CUSTOM-2 objects sent to client."
        ::= { clusterHTTPStatsEntry 191 }

clusterHTTPStatsTargetCompressContentCUSTOM3 OBJECT-TYPE
        SYNTAX     Counter64
        MAX-ACCESS read-only
        STATUS     current
        DESCRIPTION
            "Number of compressed CUSTOM-3 objects sent to client."
        ::= { clusterHTTPStatsEntry 192 }

clusterHTTPStatsTargetCompressContentOTHER OBJECT-TYPE
        SYNTAX     Counter64
        MAX-ACCESS read-only
        STATUS     current
        DESCRIPTION
            "Number of compressed OTHER objects sent to client."
        ::= { clusterHTTPStatsEntry 193 }

---------------------------------------------------------------------------
-- SSL Statistics per cluster
---------------------------------------------------------------------------
clusterSSLStatsTable OBJECT-TYPE
        SYNTAX     SEQUENCE OF ClusterSSLStatsEntry
        MAX-ACCESS not-accessible
        STATUS     current
        DESCRIPTION
            "The (conceptual) table listing the clusters SSL stats."
        ::= { clusterStats 3 }

clusterSSLStatsEntry OBJECT-TYPE
        SYNTAX     ClusterSSLStatsEntry
        MAX-ACCESS not-accessible
        STATUS     current
        DESCRIPTION
            "An entry (conceptual row) in the clusterSSLStats table."
        INDEX      { clusterSSLStatsIndex }
        ::= { clusterSSLStatsTable 1 }

ClusterSSLStatsEntry ::=
        SEQUENCE {
        clusterSSLStatsIndex 
           Integer32,
        clusterSSLStatsClusterName 
           DisplayString,
        clusterSSLStatsListenNewSessions 
           Counter64,
        clusterSSLStatsListenReusedSessions 
           Counter64,
        clusterSSLStatsListenStrongEncryption 
           Counter64,
        clusterSSLStatsListenExportEncryption 
           Counter64,
        clusterSSLStatsListenSSLv3Req 
           Counter64,
        clusterSSLStatsListenTLSv1Req 
           Counter64,
        clusterSSLStatsListenOtherSSLVersionReq 
           Counter64,
        clusterSSLStatsTargetNewSessions 
           Counter64,
        clusterSSLStatsTargetReusedSessions 
           Counter64,
        clusterSSLStatsTargetStrongEncryption 
           Counter64,
        clusterSSLStatsTargetExportEncryption 
           Counter64,
        clusterSSLStatsTargetSSLv3Req 
           Counter64,
        clusterSSLStatsTargetTLSv1Req 
           Counter64,
        clusterSSLStatsTargetOtherSSLVersionReq 
           Counter64
        }

clusterSSLStatsIndex OBJECT-TYPE
        SYNTAX     Integer32 (0..2147483647)
        MAX-ACCESS not-accessible
        STATUS     current
        DESCRIPTION
            "The Cluster Index"
        ::= { clusterSSLStatsEntry 1 }

clusterSSLStatsClusterName OBJECT-TYPE
        SYNTAX     DisplayString
        MAX-ACCESS read-only
        STATUS     current
        DESCRIPTION
            "The cluster name."
        ::= { clusterSSLStatsEntry 2 }

clusterSSLStatsListenNewSessions OBJECT-TYPE
        SYNTAX     Counter64
        MAX-ACCESS read-only
        STATUS     current
        DESCRIPTION
            "The total number of new sessions on listen side."
        ::= { clusterSSLStatsEntry 3 }

clusterSSLStatsListenReusedSessions OBJECT-TYPE
        SYNTAX     Counter64
        MAX-ACCESS read-only
        STATUS     current
        DESCRIPTION
            "The total number of reused sessions on listen side."
        ::= { clusterSSLStatsEntry 4 }

clusterSSLStatsListenStrongEncryption OBJECT-TYPE
        SYNTAX     Counter64
        MAX-ACCESS read-only
        STATUS     current
        DESCRIPTION
            "The total number of SSL request using strong encryption on listen side."
        ::= { clusterSSLStatsEntry 5 }

clusterSSLStatsListenExportEncryption OBJECT-TYPE
        SYNTAX     Counter64
        MAX-ACCESS read-only
        STATUS     current
        DESCRIPTION
            "The total number of SSL request using export encryption on listen side."
        ::= { clusterSSLStatsEntry 6 }

clusterSSLStatsListenSSLv3Req OBJECT-TYPE
        SYNTAX     Counter64
        MAX-ACCESS read-only
        STATUS     current
        DESCRIPTION
            "The total number of SSLv3 Requests on listen side."
        ::= { clusterSSLStatsEntry 7 }

clusterSSLStatsListenTLSv1Req OBJECT-TYPE
        SYNTAX     Counter64
        MAX-ACCESS read-only
        STATUS     current
        DESCRIPTION
            "The total number of TLSv1 Requests on listen side."
        ::= { clusterSSLStatsEntry 8 }

clusterSSLStatsListenOtherSSLVersionReq OBJECT-TYPE
        SYNTAX     Counter64
        MAX-ACCESS read-only
        STATUS     deprecated
        DESCRIPTION
            "The total number of OtherSSLVersionReq Requests on listen side."
        ::= { clusterSSLStatsEntry 9 }

clusterSSLStatsTargetNewSessions OBJECT-TYPE
        SYNTAX     Counter64
        MAX-ACCESS read-only
        STATUS     current
        DESCRIPTION
            "The total number of new sessions on target side."
        ::= { clusterSSLStatsEntry 10 }

clusterSSLStatsTargetReusedSessions OBJECT-TYPE
        SYNTAX     Counter64
        MAX-ACCESS read-only
        STATUS     current
        DESCRIPTION
            "The total number of reused sessions on target side."
        ::= { clusterSSLStatsEntry 11 }

clusterSSLStatsTargetStrongEncryption OBJECT-TYPE
        SYNTAX     Counter64
        MAX-ACCESS read-only
        STATUS     current
        DESCRIPTION
            "The total number of SSL request using strong encryption on target side."
        ::= { clusterSSLStatsEntry 12 }

clusterSSLStatsTargetExportEncryption OBJECT-TYPE
        SYNTAX     Counter64
        MAX-ACCESS read-only
        STATUS     current
        DESCRIPTION
            "The total number of SSL request using export encryption on target side."
        ::= { clusterSSLStatsEntry 13 }

clusterSSLStatsTargetSSLv3Req OBJECT-TYPE
        SYNTAX     Counter64
        MAX-ACCESS read-only
        STATUS     current
        DESCRIPTION
            "The total number of SSLv3 Requests on target side."
        ::= { clusterSSLStatsEntry 14 }

clusterSSLStatsTargetTLSv1Req OBJECT-TYPE
        SYNTAX     Counter64
        MAX-ACCESS read-only
        STATUS     current
        DESCRIPTION
            "The total number of TLSv1 Requests on target side."
        ::= { clusterSSLStatsEntry 15 }

clusterSSLStatsTargetOtherSSLVersionReq OBJECT-TYPE
        SYNTAX     Counter64
        MAX-ACCESS read-only
        STATUS     deprecated
        DESCRIPTION
            "The total number of OtherSSLVersionReq Requests on target side."
        ::= { clusterSSLStatsEntry 16 }

---------------------------------------------------------------------------
-- Cluster operational status table
---------------------------------------------------------------------------
clusterOperStatusTable OBJECT-TYPE
        SYNTAX     SEQUENCE OF ClusterOperStatusEntry
        MAX-ACCESS not-accessible
        STATUS     current
        DESCRIPTION
            "The (conceptual) table listing the clusters operational status."
        ::= { clusterStats 5 }

clusterOperStatusEntry OBJECT-TYPE
        SYNTAX     ClusterOperStatusEntry
        MAX-ACCESS not-accessible
        STATUS     current
        DESCRIPTION
            "An entry (conceptual row) in the clusterOperStatus table."
        INDEX      { clusterOperStatusIndex }
        ::= { clusterOperStatusTable 1 }

ClusterOperStatusEntry ::=
        SEQUENCE {
        clusterOperStatusIndex
           Integer32,
        clusterOperStatusClusterName
           DisplayString,
        clusterOperStatusStatus
           INTEGER
        }

clusterOperStatusIndex OBJECT-TYPE
        SYNTAX     Integer32 ( 0..2147483647 )
        MAX-ACCESS not-accessible
        STATUS     current
        DESCRIPTION
            "The numeric identifier used for identifying the associated
             cluster in the cluster table."
        ::= { clusterOperStatusEntry 1 }

clusterOperStatusClusterName OBJECT-TYPE
        SYNTAX     DisplayString
        MAX-ACCESS read-only
        STATUS     current
        DESCRIPTION
            "The cluster name."
        ::= { clusterOperStatusEntry 2 }

clusterOperStatusStatus OBJECT-TYPE
        SYNTAX     INTEGER { down(0), up(1) }
        MAX-ACCESS read-only
        STATUS     current
        DESCRIPTION
            "Indicates the current operational status of this cluster."
        ::= { clusterOperStatusEntry 4 }

---------------------------------------------------------------------------
-- Forwarder Level Statistics
---------------------------------------------------------------------------
forwarderStats OBJECT IDENTIFIER ::= { dxStats 3 }

forwarderIOStatsTable OBJECT-TYPE
        SYNTAX     SEQUENCE OF ForwarderIOStatsEntry
        MAX-ACCESS not-accessible
        STATUS     current
        DESCRIPTION
            "The (conceptual) table listing the forwarders IO stats."
        ::= { forwarderStats 1 }

forwarderIOStatsEntry OBJECT-TYPE
        SYNTAX     ForwarderIOStatsEntry
        MAX-ACCESS not-accessible
        STATUS     current
        DESCRIPTION
            "An entry (conceptual row) in the forwarderIOStats table."
        INDEX      { forwarderIOStatsIndex }
        ::= { forwarderIOStatsTable 1 }

ForwarderIOStatsEntry ::=
        SEQUENCE {
        forwarderIOStatsIndex 
           Integer32,
        forwarderIOStatsListenSessionActive 
           Counter64,
        forwarderIOStatsListenSessionTotal 
           Counter64,
        forwarderIOStatsListenSessionRefused 
           Counter64,
        forwarderIOStatsListenBytesIn 
           Counter64,
        forwarderIOStatsListenBytesOut 
           Counter64,
        forwarderIOStatsTargetBytesIn 
           Counter64,
        forwarderIOStatsTargetBytesOut 
           Counter64,
        forwarderIOStatsListenDeadStickyThost 
           Counter64,
        forwarderIOStatsListenDeletedStickyThost 
           Counter64,
        forwarderIOStatsTargetDownStickyThost 
           Counter64
        }

---------------------------------------------------------------------------
-- Session Statistics
---------------------------------------------------------------------------
forwarderIOStatsIndex OBJECT-TYPE
        SYNTAX     Integer32 (0..2147483647)
        MAX-ACCESS not-accessible
        STATUS     current
        DESCRIPTION
            "The Forwarder Index"
        ::= { forwarderIOStatsEntry 1 }

forwarderIOStatsListenSessionActive OBJECT-TYPE
        SYNTAX     Counter64
        MAX-ACCESS read-only
        STATUS     current
        DESCRIPTION
            "The active number of sessions."
        ::= { forwarderIOStatsEntry 2 }

forwarderIOStatsListenSessionTotal OBJECT-TYPE
        SYNTAX     Counter64
        MAX-ACCESS read-only
        STATUS     current
        DESCRIPTION
            "The total number of sessions handled."
        ::= { forwarderIOStatsEntry 3 }

forwarderIOStatsListenSessionRefused OBJECT-TYPE
        SYNTAX     Counter64
        MAX-ACCESS read-only
        STATUS     current
        DESCRIPTION
            "The total number of sessions refused."
        ::= { forwarderIOStatsEntry 4 }

---------------------------------------------------------------------------
-- Byte Statistics
---------------------------------------------------------------------------
forwarderIOStatsListenBytesIn OBJECT-TYPE
        SYNTAX     Counter64
        MAX-ACCESS read-only
        STATUS     current
        DESCRIPTION
            "Total number of bytes in."
        ::= { forwarderIOStatsEntry 5 }

forwarderIOStatsListenBytesOut OBJECT-TYPE
        SYNTAX     Counter64
        MAX-ACCESS read-only
        STATUS     current
        DESCRIPTION
            "Total number of bytes out."
        ::= { forwarderIOStatsEntry 6 }

forwarderIOStatsTargetBytesIn OBJECT-TYPE
        SYNTAX     Counter64
        MAX-ACCESS read-only
        STATUS     current
        DESCRIPTION
            "Total number of bytes in."
        ::= { forwarderIOStatsEntry 7 }

forwarderIOStatsTargetBytesOut OBJECT-TYPE
        SYNTAX     Counter64
        MAX-ACCESS read-only
        STATUS     current
        DESCRIPTION
            "Total number of bytes out."
        ::= { forwarderIOStatsEntry 10 }

forwarderIOStatsListenDeadStickyThost OBJECT-TYPE
        SYNTAX     Counter64
        MAX-ACCESS read-only
        STATUS     current
        DESCRIPTION
            "Number of times client IP sticky target was dead."
        ::= { forwarderIOStatsEntry 11 }

forwarderIOStatsListenDeletedStickyThost OBJECT-TYPE
        SYNTAX     Counter64
        MAX-ACCESS read-only
        STATUS     current
        DESCRIPTION
            "Number of times client IP sticky target was deleted."
        ::= { forwarderIOStatsEntry 12 }

forwarderIOStatsTargetDownStickyThost OBJECT-TYPE
        SYNTAX     Counter64
        MAX-ACCESS read-only
        STATUS     current
        DESCRIPTION
            "Number of times client IP sticky target service was down."
        ::= { forwarderIOStatsEntry 13 }


---------------------------------------------------------------------------
-- SSL Statistics per forwarder
---------------------------------------------------------------------------
forwarderSSLStatsTable OBJECT-TYPE
        SYNTAX     SEQUENCE OF ForwarderSSLStatsEntry
        MAX-ACCESS not-accessible
        STATUS     current
        DESCRIPTION
            "The (conceptual) table listing the forwarders SSL stats."
        ::= { forwarderStats 2 }

forwarderSSLStatsEntry OBJECT-TYPE
        SYNTAX     ForwarderSSLStatsEntry
        MAX-ACCESS not-accessible
        STATUS     current
        DESCRIPTION
            "An entry (conceptual row) in the forwarderSSLStats table."
        INDEX      { forwarderSSLStatsIndex }
        ::= { forwarderSSLStatsTable 1 }

ForwarderSSLStatsEntry ::=
        SEQUENCE {
        forwarderSSLStatsIndex 
           Integer32,
        forwarderSSLStatsForwarderName 
           DisplayString,
        forwarderSSLStatsListenNewSessions 
           Counter64,
        forwarderSSLStatsListenReusedSessions 
           Counter64,
        forwarderSSLStatsListenStrongEncryption 
           Counter64,
        forwarderSSLStatsListenExportEncryption 
           Counter64,
        forwarderSSLStatsListenSSLv3Req 
           Counter64,
        forwarderSSLStatsListenTLSv1Req 
           Counter64,
        forwarderSSLStatsListenOtherSSLVersionReq 
           Counter64,
        forwarderSSLStatsTargetNewSessions 
           Counter64,
        forwarderSSLStatsTargetReusedSessions 
           Counter64,
        forwarderSSLStatsTargetStrongEncryption 
           Counter64,
        forwarderSSLStatsTargetExportEncryption 
           Counter64,
        forwarderSSLStatsTargetSSLv3Req 
           Counter64,
        forwarderSSLStatsTargetTLSv1Req 
           Counter64,
        forwarderSSLStatsTargetOtherSSLVersionReq 
           Counter64
        }

forwarderSSLStatsIndex OBJECT-TYPE
        SYNTAX     Integer32 (0..2147483647)
        MAX-ACCESS not-accessible
        STATUS     current
        DESCRIPTION
            "The Forwarder Index"
        ::= { forwarderSSLStatsEntry 1 }

forwarderSSLStatsForwarderName OBJECT-TYPE
        SYNTAX     DisplayString
        MAX-ACCESS read-only
        STATUS     current
        DESCRIPTION
            "The forwarder name."
        ::= { forwarderSSLStatsEntry 2 }

forwarderSSLStatsListenNewSessions OBJECT-TYPE
        SYNTAX     Counter64
        MAX-ACCESS read-only
        STATUS     current
        DESCRIPTION
            "The total number of new sessions on listen side."
        ::= { forwarderSSLStatsEntry 3 }

forwarderSSLStatsListenReusedSessions OBJECT-TYPE
        SYNTAX     Counter64
        MAX-ACCESS read-only
        STATUS     current
        DESCRIPTION
            "The total number of reused sessions on listen side."
        ::= { forwarderSSLStatsEntry 4 }

forwarderSSLStatsListenStrongEncryption OBJECT-TYPE
        SYNTAX     Counter64
        MAX-ACCESS read-only
        STATUS     current
        DESCRIPTION
            "The total number of SSL request using strong encryption on listen side."
        ::= { forwarderSSLStatsEntry 5 }

forwarderSSLStatsListenExportEncryption OBJECT-TYPE
        SYNTAX     Counter64
        MAX-ACCESS read-only
        STATUS     current
        DESCRIPTION
            "The total number of SSL request using export encryption on listen side."
        ::= { forwarderSSLStatsEntry 6 }

forwarderSSLStatsListenSSLv3Req OBJECT-TYPE
        SYNTAX     Counter64
        MAX-ACCESS read-only
        STATUS     current
        DESCRIPTION
            "The total number of SSLv3 Requests on listen side."
        ::= { forwarderSSLStatsEntry 7 }

forwarderSSLStatsListenTLSv1Req OBJECT-TYPE
        SYNTAX     Counter64
        MAX-ACCESS read-only
        STATUS     current
        DESCRIPTION
            "The total number of TLSv1 Requests on listen side."
        ::= { forwarderSSLStatsEntry 8 }

forwarderSSLStatsListenOtherSSLVersionReq OBJECT-TYPE
        SYNTAX     Counter64
        MAX-ACCESS read-only
        STATUS     deprecated
        DESCRIPTION
            "The total number of OtherSSLVersionReq Requests on listen side."
        ::= { forwarderSSLStatsEntry 9 }

forwarderSSLStatsTargetNewSessions OBJECT-TYPE
        SYNTAX     Counter64
        MAX-ACCESS read-only
        STATUS     current
        DESCRIPTION
            "The total number of new sessions on target side."
        ::= { forwarderSSLStatsEntry 10 }

forwarderSSLStatsTargetReusedSessions OBJECT-TYPE
        SYNTAX     Counter64
        MAX-ACCESS read-only
        STATUS     current
        DESCRIPTION
            "The total number of reused sessions on target side."
        ::= { forwarderSSLStatsEntry 11 }

forwarderSSLStatsTargetStrongEncryption OBJECT-TYPE
        SYNTAX     Counter64
        MAX-ACCESS read-only
        STATUS     current
        DESCRIPTION
            "The total number of SSL request using strong encryption on target side."
        ::= { forwarderSSLStatsEntry 12 }

forwarderSSLStatsTargetExportEncryption OBJECT-TYPE
        SYNTAX     Counter64
        MAX-ACCESS read-only
        STATUS     current
        DESCRIPTION
            "The total number of SSL request using export encryption on target side."
        ::= { forwarderSSLStatsEntry 13 }

forwarderSSLStatsTargetSSLv3Req OBJECT-TYPE
        SYNTAX     Counter64
        MAX-ACCESS read-only
        STATUS     current
        DESCRIPTION
            "The total number of SSLv3 Requests on target side."
        ::= { forwarderSSLStatsEntry 14 }

forwarderSSLStatsTargetTLSv1Req OBJECT-TYPE
        SYNTAX     Counter64
        MAX-ACCESS read-only
        STATUS     current
        DESCRIPTION
            "The total number of TLSv1 Requests on target side."
        ::= { forwarderSSLStatsEntry 15 }

forwarderSSLStatsTargetOtherSSLVersionReq OBJECT-TYPE
        SYNTAX     Counter64
        MAX-ACCESS read-only
        STATUS     deprecated
        DESCRIPTION
            "The total number of OtherSSLVersionReq Requests on target side."
        ::= { forwarderSSLStatsEntry 16 }

---------------------------------------------------------------------------
-- Redirector Level Statistics
---------------------------------------------------------------------------
redirectorStats OBJECT IDENTIFIER ::= { dxStats 4 }

---------------------------------------------------------------------------
-- Redirector Level IO Statistics
---------------------------------------------------------------------------
redirectorIOStatsTable OBJECT-TYPE
        SYNTAX     SEQUENCE OF RedirectorIOStatsEntry
        MAX-ACCESS not-accessible
        STATUS     current
        DESCRIPTION
            "The (conceptual) table listing the redirectors IO stats."
        ::= { redirectorStats 1 }

redirectorIOStatsEntry OBJECT-TYPE
        SYNTAX     RedirectorIOStatsEntry
        MAX-ACCESS not-accessible
        STATUS     current
        DESCRIPTION
            "An entry (conceptual row) in the redirectorIOStats table."
        INDEX      { redirectorIOStatsIndex }
        ::= { redirectorIOStatsTable 1 }

RedirectorIOStatsEntry ::=
        SEQUENCE {
        redirectorIOStatsIndex 
           Integer32,
        redirectorIOStatsListenSessionActive 
           Counter64,
        redirectorIOStatsListenSessionTotal 
           Counter64,
        redirectorIOStatsListenSessionRefused 
           Counter64,
        redirectorIOStatsListenReqActive 
           Counter64,
        redirectorIOStatsListenReqTotal 
           Counter64,
        redirectorIOStatsListenBytesIn 
           Counter64,
        redirectorIOStatsListenBytesOut 
           Counter64
        }

---------------------------------------------------------------------------
-- Session Statistics
---------------------------------------------------------------------------
redirectorIOStatsIndex OBJECT-TYPE
        SYNTAX     Integer32 (0..2147483647)
        MAX-ACCESS not-accessible
        STATUS     current
        DESCRIPTION
            "The Redirector Index"
        ::= { redirectorIOStatsEntry 1 }

redirectorIOStatsListenSessionActive OBJECT-TYPE
        SYNTAX     Counter64
        MAX-ACCESS read-only
        STATUS     current
        DESCRIPTION
            "The active number of sessions."
        ::= { redirectorIOStatsEntry 2 }

redirectorIOStatsListenSessionTotal OBJECT-TYPE
        SYNTAX     Counter64
        MAX-ACCESS read-only
        STATUS     current
        DESCRIPTION
            "The total number of sessions handled."
        ::= { redirectorIOStatsEntry 3 }

redirectorIOStatsListenSessionRefused OBJECT-TYPE
        SYNTAX     Counter64
        MAX-ACCESS read-only
        STATUS     current
        DESCRIPTION
            "The total number of sessions refused."
        ::= { redirectorIOStatsEntry 4 }

---------------------------------------------------------------------------
-- Request Statistics
---------------------------------------------------------------------------
redirectorIOStatsListenReqActive OBJECT-TYPE
        SYNTAX     Counter64
        MAX-ACCESS read-only
        STATUS     deprecated
        DESCRIPTION
            "The active number of requests."
        ::= { redirectorIOStatsEntry 5 }

redirectorIOStatsListenReqTotal OBJECT-TYPE
        SYNTAX     Counter64
        MAX-ACCESS read-only
        STATUS     deprecated
        DESCRIPTION
            "The total number of requests."
        ::= { redirectorIOStatsEntry 6 }

---------------------------------------------------------------------------
-- Byte Statistics
---------------------------------------------------------------------------
redirectorIOStatsListenBytesIn OBJECT-TYPE
        SYNTAX     Counter64
        MAX-ACCESS read-only
        STATUS     current
        DESCRIPTION
            "Total number of bytes in."
        ::= { redirectorIOStatsEntry 7 }

redirectorIOStatsListenBytesOut OBJECT-TYPE
        SYNTAX     Counter64
        MAX-ACCESS read-only
        STATUS     current
        DESCRIPTION
            "Total number of bytes out."
        ::= { redirectorIOStatsEntry 8 }

---------------------------------------------------------------------------
-- SSL Statistics per redirector
---------------------------------------------------------------------------
redirectorSSLStatsTable OBJECT-TYPE
        SYNTAX     SEQUENCE OF RedirectorSSLStatsEntry
        MAX-ACCESS not-accessible
        STATUS     current
        DESCRIPTION
            "The (conceptual) table listing the redirectors SSL stats."
        ::= { redirectorStats 2 }

redirectorSSLStatsEntry OBJECT-TYPE
        SYNTAX     RedirectorSSLStatsEntry
        MAX-ACCESS not-accessible
        STATUS     current
        DESCRIPTION
            "An entry (conceptual row) in the redirectorSSLStats table."
        INDEX      { redirectorSSLStatsIndex }
        ::= { redirectorSSLStatsTable 1 }

RedirectorSSLStatsEntry ::=
        SEQUENCE {
        redirectorSSLStatsIndex 
           Integer32,
        redirectorSSLStatsListenNewSessions 
           Counter64,
        redirectorSSLStatsListenReusedSessions 
           Counter64,
        redirectorSSLStatsListenStrongEncryption 
           Counter64,
        redirectorSSLStatsListenExportEncryption 
           Counter64,
        redirectorSSLStatsListenSSLv3Req 
           Counter64,
        redirectorSSLStatsListenTLSv1Req 
           Counter64,
        redirectorSSLStatsListenOtherSSLVersionReq 
           Counter64
        }

redirectorSSLStatsIndex OBJECT-TYPE
        SYNTAX     Integer32 (0..2147483647)
        MAX-ACCESS not-accessible
        STATUS     current
        DESCRIPTION
            "The Redirector Index"
        ::= { redirectorSSLStatsEntry 1 }

redirectorSSLStatsListenNewSessions OBJECT-TYPE
        SYNTAX     Counter64
        MAX-ACCESS read-only
        STATUS     current
        DESCRIPTION
            "The total number of new sessions on listen side."
        ::= { redirectorSSLStatsEntry 2 }

redirectorSSLStatsListenReusedSessions OBJECT-TYPE
        SYNTAX     Counter64
        MAX-ACCESS read-only
        STATUS     current
        DESCRIPTION
            "The total number of reused sessions on listen side."
        ::= { redirectorSSLStatsEntry 3 }

redirectorSSLStatsListenStrongEncryption OBJECT-TYPE
        SYNTAX     Counter64
        MAX-ACCESS read-only
        STATUS     current
        DESCRIPTION
            "The total number of SSL request using strong encryption on listen side."
        ::= { redirectorSSLStatsEntry 4 }

redirectorSSLStatsListenExportEncryption OBJECT-TYPE
        SYNTAX     Counter64
        MAX-ACCESS read-only
        STATUS     current
        DESCRIPTION
            "The total number of SSL request using export encryption on listen side."
        ::= { redirectorSSLStatsEntry 5 }

redirectorSSLStatsListenSSLv3Req OBJECT-TYPE
        SYNTAX     Counter64
        MAX-ACCESS read-only
        STATUS     current
        DESCRIPTION
            "The total number of SSLv3 Requests on listen side."
        ::= { redirectorSSLStatsEntry 6 }

redirectorSSLStatsListenTLSv1Req OBJECT-TYPE
        SYNTAX     Counter64
        MAX-ACCESS read-only
        STATUS     current
        DESCRIPTION
            "The total number of TLSv1 Requests on listen side."
        ::= { redirectorSSLStatsEntry 7 }

redirectorSSLStatsListenOtherSSLVersionReq OBJECT-TYPE
        SYNTAX     Counter64
        MAX-ACCESS read-only
        STATUS     deprecated
        DESCRIPTION
            "The total number of OtherSSLVersionReq Requests on listen side."
        ::= { redirectorSSLStatsEntry 8 }

---------------------------------------------------------------------------
-- TargetServer Level Statistics
---------------------------------------------------------------------------
targetServerStats OBJECT IDENTIFIER ::= { dxStats 5 }

targetServerIOStatsTable OBJECT-TYPE
        SYNTAX     SEQUENCE OF TargetServerIOStatsEntry
        MAX-ACCESS not-accessible
        STATUS     current
        DESCRIPTION
            "The (conceptual) table listing the targetServers IO stats."
        ::= { targetServerStats 1 }

targetServerIOStatsEntry OBJECT-TYPE
        SYNTAX     TargetServerIOStatsEntry
        MAX-ACCESS not-accessible
        STATUS     current
        DESCRIPTION
            "An entry (conceptual row) in the targetServerIOStats table."
        INDEX      { targetServerIOStatsIndex }
        ::= { targetServerIOStatsTable 1 }

TargetServerIOStatsEntry ::=
        SEQUENCE {
        targetServerIOStatsIndex 
           Integer32,
        tsIOStatsClusterName
           DisplayString,
        tsIOStatsPhysicalServer 
           DisplayString,
        tsIOStatsBytesIn 
           Counter64,
        tsIOStatsBytesOut 
           Counter64,
        tsIOStatsDownStickyThost 
           Counter64
        }

---------------------------------------------------------------------------
-- Session Statistics
---------------------------------------------------------------------------
targetServerIOStatsIndex OBJECT-TYPE
        SYNTAX     Integer32 (0..2147483647)
        MAX-ACCESS not-accessible
        STATUS     current
        DESCRIPTION
            "The TargetServer Index"
        ::= { targetServerIOStatsEntry 1 }

tsIOStatsClusterName OBJECT-TYPE
        SYNTAX     DisplayString
        MAX-ACCESS read-only
        STATUS     current
        DESCRIPTION
            "The cluster name."
        ::= { targetServerIOStatsEntry 2 }

tsIOStatsPhysicalServer OBJECT-TYPE
        SYNTAX     DisplayString
        MAX-ACCESS read-only
        STATUS     current
        DESCRIPTION
            "The physical server's IP address and port ."
        ::= { targetServerIOStatsEntry 3 }

---------------------------------------------------------------------------
-- Byte Statistics
---------------------------------------------------------------------------
tsIOStatsBytesIn OBJECT-TYPE
        SYNTAX     Counter64
        MAX-ACCESS read-only
        STATUS     current
        DESCRIPTION
            "Total number of bytes in."
        ::= { targetServerIOStatsEntry 5 }

tsIOStatsBytesOut OBJECT-TYPE
        SYNTAX     Counter64
        MAX-ACCESS read-only
        STATUS     current
        DESCRIPTION
            "Total number of bytes out."
        ::= { targetServerIOStatsEntry 6 }

tsIOStatsDownStickyThost OBJECT-TYPE
        SYNTAX     Counter64
        MAX-ACCESS read-only
        STATUS     current
        DESCRIPTION
            "Number of times client IP sticky target service was down."
        ::= { targetServerIOStatsEntry 7 }

---------------------------------------------------------------------------
-- HTTP Statistics per targetServer
---------------------------------------------------------------------------
targetServerHTTPStatsTable OBJECT-TYPE
        SYNTAX     SEQUENCE OF TargetServerHTTPStatsEntry
        MAX-ACCESS not-accessible
        STATUS     current
        DESCRIPTION
            "The (conceptual) table listing the targetServers HTTP stats."
        ::= { targetServerStats 2 }

targetServerHTTPStatsEntry OBJECT-TYPE
        SYNTAX     TargetServerHTTPStatsEntry
        MAX-ACCESS not-accessible
        STATUS     current
        DESCRIPTION
            "An entry (conceptual row) in the targetServerHTTPStats table."
        INDEX      { tsHTTPStatsIndex }
        ::= { targetServerHTTPStatsTable 1 }

TargetServerHTTPStatsEntry ::=
        SEQUENCE {
        tsHTTPStatsIndex 
           Integer32,
        tsHTTPStatsClusterName
           DisplayString,
        tsHTTPStatsPhysicalServer 
           DisplayString,

        tsHTTPStatsTargetResponseCode100 
           Counter64,
        tsHTTPStatsTargetResponseCode200 
           Counter64,
        tsHTTPStatsTargetResponseCode302 
           Counter64,
        tsHTTPStatsTargetResponseCode304 
           Counter64,
        tsHTTPStatsTargetResponseCode3xx 
           Counter64,
        tsHTTPStatsTargetResponseCode404 
           Counter64,
        tsHTTPStatsTargetResponseCode4xx
           Counter64,
        tsHTTPStatsTargetResponseCode5xx
           Counter64,
        tsHTTPStatsTargetResponseCodeOthers
           Counter64,

        tsHTTPStatsTargetContentGIF
           Counter64,
        tsHTTPStatsTargetContentJPEG
           Counter64,
        tsHTTPStatsTargetContentHTML
           Counter64,
        tsHTTPStatsTargetContentCSS
           Counter64,
        tsHTTPStatsTargetContentXML
           Counter64,
        tsHTTPStatsTargetContentTEXT
           Counter64,
        tsHTTPStatsTargetContentJAVASCRIPT
           Counter64,
        tsHTTPStatsTargetContentFLASH
           Counter64,
        tsHTTPStatsTargetContentOthers
           Counter64,

        tsHTTPStatsTargetBytesInGIF
           Counter64,
        tsHTTPStatsTargetBytesInJPEG
           Counter64,
        tsHTTPStatsTargetBytesInHTML
           Counter64,
        tsHTTPStatsTargetBytesInCSS
           Counter64,
        tsHTTPStatsTargetBytesInXML
           Counter64,
        tsHTTPStatsTargetBytesInTEXT
           Counter64,
        tsHTTPStatsTargetBytesInJAVASCRIPT
           Counter64,
        tsHTTPStatsTargetBytesInFLASH
           Counter64,
        tsHTTPStatsTargetBytesInOthers
           Counter64,

        tsHTTPStatsTargetBytesOutGIF
           Counter64,
        tsHTTPStatsTargetBytesOutJPEG
           Counter64,
        tsHTTPStatsTargetBytesOutHTML
           Counter64,
        tsHTTPStatsTargetBytesOutCSS
           Counter64,
        tsHTTPStatsTargetBytesOutXML
           Counter64,
        tsHTTPStatsTargetBytesOutTEXT
           Counter64,
        tsHTTPStatsTargetBytesOutJAVASCRIPT
           Counter64,
        tsHTTPStatsTargetBytesOutFLASH
           Counter64,
        tsHTTPStatsTargetBytesOutOthers
           Counter64,

        tsHTTPStatsTargetResponseCode1xx
           Counter64,
        tsHTTPStatsTargetResponseCode101
           Counter64,
        tsHTTPStatsTargetResponseCode102
           Counter64,

        tsHTTPStatsTargetResponseCode2xx
           Counter64,
        tsHTTPStatsTargetResponseCode201
           Counter64,
        tsHTTPStatsTargetResponseCode202
           Counter64,
        tsHTTPStatsTargetResponseCode203
           Counter64,
        tsHTTPStatsTargetResponseCode204
           Counter64,
        tsHTTPStatsTargetResponseCode205
           Counter64,
        tsHTTPStatsTargetResponseCode206
           Counter64,
        tsHTTPStatsTargetResponseCode207
           Counter64,

        tsHTTPStatsTargetResponseCode300
           Counter64,
        tsHTTPStatsTargetResponseCode301
           Counter64,
        tsHTTPStatsTargetResponseCode303
           Counter64,
        tsHTTPStatsTargetResponseCode305
           Counter64,
        tsHTTPStatsTargetResponseCode306
           Counter64,
        tsHTTPStatsTargetResponseCode307
           Counter64,

        tsHTTPStatsTargetResponseCode400
           Counter64,
        tsHTTPStatsTargetResponseCode401
           Counter64,
        tsHTTPStatsTargetResponseCode402
           Counter64,
        tsHTTPStatsTargetResponseCode403
           Counter64,
        tsHTTPStatsTargetResponseCode405
           Counter64,
        tsHTTPStatsTargetResponseCode406
           Counter64,
        tsHTTPStatsTargetResponseCode407
           Counter64,
        tsHTTPStatsTargetResponseCode408
           Counter64,
        tsHTTPStatsTargetResponseCode409
           Counter64,
        tsHTTPStatsTargetResponseCode410
           Counter64,
        tsHTTPStatsTargetResponseCode411
           Counter64,
        tsHTTPStatsTargetResponseCode412
           Counter64,
        tsHTTPStatsTargetResponseCode413
           Counter64,
        tsHTTPStatsTargetResponseCode414
           Counter64,
        tsHTTPStatsTargetResponseCode415
           Counter64,
        tsHTTPStatsTargetResponseCode416
           Counter64,
        tsHTTPStatsTargetResponseCode417
           Counter64,
        tsHTTPStatsTargetResponseCode422
           Counter64,
        tsHTTPStatsTargetResponseCode423
           Counter64,
        tsHTTPStatsTargetResponseCode424
           Counter64,
        tsHTTPStatsTargetResponseCode425
           Counter64,

        tsHTTPStatsTargetResponseCode500
           Counter64,
        tsHTTPStatsTargetResponseCode501
           Counter64,
        tsHTTPStatsTargetResponseCode502
           Counter64,
        tsHTTPStatsTargetResponseCode503
           Counter64,
        tsHTTPStatsTargetResponseCode504
           Counter64,
        tsHTTPStatsTargetResponseCode505
           Counter64,
        tsHTTPStatsTargetResponseCode506
           Counter64,
        tsHTTPStatsTargetResponseCode507
           Counter64,

        tsHTTPStatsTargetContentXCOMPONENT
           Counter64,
        tsHTTPStatsTargetContentOCTETSTREAM
           Counter64,
        tsHTTPStatsTargetContentMSWORD
           Counter64,
        tsHTTPStatsTargetContentMSEXCEL
           Counter64,
        tsHTTPStatsTargetContentMSPOWERPOINT
           Counter64,
        tsHTTPStatsTargetContentCUSTOM1
           Counter64,
        tsHTTPStatsTargetContentCUSTOM2
           Counter64,
        tsHTTPStatsTargetContentCUSTOM3
           Counter64,

        tsHTTPStatsTargetBytesInXCOMPONENT
           Counter64,
        tsHTTPStatsTargetBytesInOCTETSTREAM
           Counter64,
        tsHTTPStatsTargetBytesInMSWORD
           Counter64,
        tsHTTPStatsTargetBytesInMSEXCEL
           Counter64,
        tsHTTPStatsTargetBytesInMSPOWERPOINT
           Counter64,
        tsHTTPStatsTargetBytesInCUSTOM1
           Counter64,
        tsHTTPStatsTargetBytesInCUSTOM2
           Counter64,
        tsHTTPStatsTargetBytesInCUSTOM3
           Counter64,

        tsHTTPStatsTargetBytesOutXCOMPONENT
           Counter64,
        tsHTTPStatsTargetBytesOutOCTETSTREAM
           Counter64,
        tsHTTPStatsTargetBytesOutMSWORD
           Counter64,
        tsHTTPStatsTargetBytesOutMSEXCEL
           Counter64,
        tsHTTPStatsTargetBytesOutMSPOWERPOINT
           Counter64,
        tsHTTPStatsTargetBytesOutCUSTOM1
           Counter64,
        tsHTTPStatsTargetBytesOutCUSTOM2
           Counter64,
        tsHTTPStatsTargetBytesOutCUSTOM3
           Counter64
        }

---------------------------------------------------------------------------
-- Request Statistics
---------------------------------------------------------------------------
tsHTTPStatsIndex OBJECT-TYPE
        SYNTAX     Integer32 (0..2147483647)
        MAX-ACCESS not-accessible
        STATUS     current
        DESCRIPTION
            "The TargetServer Index"
        ::= { targetServerHTTPStatsEntry 1 }

tsHTTPStatsClusterName OBJECT-TYPE
        SYNTAX     DisplayString
        MAX-ACCESS read-only
        STATUS     current
        DESCRIPTION
            "The cluster to which this physical server is bound."
        ::= { targetServerHTTPStatsEntry 2 }

tsHTTPStatsPhysicalServer OBJECT-TYPE
        SYNTAX     DisplayString
        MAX-ACCESS read-only
        STATUS     current
        DESCRIPTION
            "The physical server's IP address and port ."
        ::= { targetServerHTTPStatsEntry 3 }

tsHTTPStatsTargetResponseCode100 OBJECT-TYPE
        SYNTAX     Counter64
        MAX-ACCESS read-only
        STATUS     current
        DESCRIPTION
            "The total number of HTTP 100 response code."
        ::= { targetServerHTTPStatsEntry 5 }

tsHTTPStatsTargetResponseCode200 OBJECT-TYPE
        SYNTAX     Counter64
        MAX-ACCESS read-only
        STATUS     current
        DESCRIPTION
            "The total number of HTTP 200 response code."
        ::= { targetServerHTTPStatsEntry 6 }

tsHTTPStatsTargetResponseCode302 OBJECT-TYPE
        SYNTAX     Counter64
        MAX-ACCESS read-only
        STATUS     current
        DESCRIPTION
            "The total number of HTTP 302 response code."
        ::= { targetServerHTTPStatsEntry 7 }

tsHTTPStatsTargetResponseCode304 OBJECT-TYPE
        SYNTAX     Counter64
        MAX-ACCESS read-only
        STATUS     current
        DESCRIPTION
            "The total number of HTTP 304 response code."
        ::= { targetServerHTTPStatsEntry 8 }

tsHTTPStatsTargetResponseCode3xx OBJECT-TYPE
        SYNTAX     Counter64
        MAX-ACCESS read-only
        STATUS     current
        DESCRIPTION
            "The total number of HTTP 3xx response code."
        ::= { targetServerHTTPStatsEntry 9 }

tsHTTPStatsTargetResponseCode404 OBJECT-TYPE
        SYNTAX     Counter64
        MAX-ACCESS read-only
        STATUS     current
        DESCRIPTION
            "The total number of HTTP 404 response code."
        ::= { targetServerHTTPStatsEntry 10 }

tsHTTPStatsTargetResponseCode4xx OBJECT-TYPE
        SYNTAX     Counter64
        MAX-ACCESS read-only
        STATUS     current
        DESCRIPTION
            "The total number of HTTP 4xx response code."
        ::= { targetServerHTTPStatsEntry 11 }

tsHTTPStatsTargetResponseCode5xx OBJECT-TYPE
        SYNTAX     Counter64
        MAX-ACCESS read-only
        STATUS     current
        DESCRIPTION
            "The total number of HTTP 5xx response code."
        ::= { targetServerHTTPStatsEntry 12 }

tsHTTPStatsTargetResponseCodeOthers OBJECT-TYPE
        SYNTAX     Counter64
        MAX-ACCESS read-only
        STATUS     current
        DESCRIPTION
            "The total number of Others HTTP response codes."
        ::= { targetServerHTTPStatsEntry 13 }

tsHTTPStatsTargetContentGIF OBJECT-TYPE
        SYNTAX     Counter64
        MAX-ACCESS read-only
        STATUS     current
        DESCRIPTION
            "The total number of responses with content type GIF."
        ::= { targetServerHTTPStatsEntry 14 }

tsHTTPStatsTargetContentJPEG OBJECT-TYPE
        SYNTAX     Counter64
        MAX-ACCESS read-only
        STATUS     current
        DESCRIPTION
            "The total number of responses with content type JPEG."
        ::= { targetServerHTTPStatsEntry 15 }

tsHTTPStatsTargetContentHTML OBJECT-TYPE
        SYNTAX     Counter64
        MAX-ACCESS read-only
        STATUS     current
        DESCRIPTION
            "The total number of responses with content type HTML."
        ::= { targetServerHTTPStatsEntry 16 }

tsHTTPStatsTargetContentCSS OBJECT-TYPE
        SYNTAX     Counter64
        MAX-ACCESS read-only
        STATUS     current
        DESCRIPTION
            "The total number of responses with content type CSS."
        ::= { targetServerHTTPStatsEntry 17 }

tsHTTPStatsTargetContentXML OBJECT-TYPE
        SYNTAX     Counter64
        MAX-ACCESS read-only
        STATUS     current
        DESCRIPTION
            "The total number of responses with content type XML."
        ::= { targetServerHTTPStatsEntry 18 }

tsHTTPStatsTargetContentTEXT OBJECT-TYPE
        SYNTAX     Counter64
        MAX-ACCESS read-only
        STATUS     current
        DESCRIPTION
            "The total number of responses with content type TEXT."
        ::= { targetServerHTTPStatsEntry 19 }

tsHTTPStatsTargetContentJAVASCRIPT OBJECT-TYPE
        SYNTAX     Counter64
        MAX-ACCESS read-only
        STATUS     current
        DESCRIPTION
            "The total number of responses with content type JAVASCRIPT."
        ::= { targetServerHTTPStatsEntry 20 }

tsHTTPStatsTargetContentFLASH OBJECT-TYPE
        SYNTAX     Counter64
        MAX-ACCESS read-only
        STATUS     current
        DESCRIPTION
            "The total number of responses with content type FLASH."
        ::= { targetServerHTTPStatsEntry 21 }

tsHTTPStatsTargetContentOthers OBJECT-TYPE
        SYNTAX     Counter64
        MAX-ACCESS read-only
        STATUS     current
        DESCRIPTION
            "The total number of responses with content Other types."
        ::= { targetServerHTTPStatsEntry 22 }


tsHTTPStatsTargetBytesInGIF OBJECT-TYPE
        SYNTAX     Counter64
        MAX-ACCESS read-only
        STATUS     current
        DESCRIPTION
            "Total number of HTTP response body bytes received with the 
             given content type (excluding chunk headers) BEFORE the TX 
             performs its HTTP-level response body processing. HTTP response 
             headers and chunk headers/trailers are not counted, but any 
             compressed or uncompressed HTTP data is counted. Responses that 
             do not have a body (e.g. 304) are not counted."
        ::= { targetServerHTTPStatsEntry 23 }

tsHTTPStatsTargetBytesInJPEG OBJECT-TYPE
        SYNTAX     Counter64
        MAX-ACCESS read-only
        STATUS     current
        DESCRIPTION
            "Total number of HTTP response body bytes received with the 
             given content type (excluding chunk headers) BEFORE the TX 
             performs its HTTP-level response body processing. HTTP response 
             headers and chunk headers/trailers are not counted, but any 
             compressed or uncompressed HTTP data is counted. Responses that 
             do not have a body (e.g. 304) are not counted."
        ::= { targetServerHTTPStatsEntry 24 }

tsHTTPStatsTargetBytesInHTML OBJECT-TYPE
        SYNTAX     Counter64
        MAX-ACCESS read-only
        STATUS     current
        DESCRIPTION
            "Total number of HTTP response body bytes received with the 
             given content type (excluding chunk headers) BEFORE the TX 
             performs its HTTP-level response body processing. HTTP response 
             headers and chunk headers/trailers are not counted, but any 
             compressed or uncompressed HTTP data is counted. Responses that 
             do not have a body (e.g. 304) are not counted."
        ::= { targetServerHTTPStatsEntry 25 }

tsHTTPStatsTargetBytesInCSS OBJECT-TYPE
        SYNTAX     Counter64
        MAX-ACCESS read-only
        STATUS     current
        DESCRIPTION
            "Total number of HTTP response body bytes received with the 
             given content type (excluding chunk headers) BEFORE the TX 
             performs its HTTP-level response body processing. HTTP response 
             headers and chunk headers/trailers are not counted, but any 
             compressed or uncompressed HTTP data is counted. Responses that 
             do not have a body (e.g. 304) are not counted."
        ::= { targetServerHTTPStatsEntry 26 }

tsHTTPStatsTargetBytesInXML OBJECT-TYPE
        SYNTAX     Counter64
        MAX-ACCESS read-only
        STATUS     current
        DESCRIPTION
            "Total number of HTTP response body bytes received with the 
             given content type (excluding chunk headers) BEFORE the TX 
             performs its HTTP-level response body processing. HTTP response 
             headers and chunk headers/trailers are not counted, but any 
             compressed or uncompressed HTTP data is counted. Responses that 
             do not have a body (e.g. 304) are not counted."
        ::= { targetServerHTTPStatsEntry 27 }

tsHTTPStatsTargetBytesInTEXT OBJECT-TYPE
        SYNTAX     Counter64
        MAX-ACCESS read-only
        STATUS     current
        DESCRIPTION
            "Total number of HTTP response body bytes received with the 
             given content type (excluding chunk headers) BEFORE the TX 
             performs its HTTP-level response body processing. HTTP response 
             headers and chunk headers/trailers are not counted, but any 
             compressed or uncompressed HTTP data is counted. Responses that 
             do not have a body (e.g. 304) are not counted."
        ::= { targetServerHTTPStatsEntry 28 }

tsHTTPStatsTargetBytesInJAVASCRIPT OBJECT-TYPE
        SYNTAX     Counter64
        MAX-ACCESS read-only
        STATUS     current
        DESCRIPTION
            "Total number of HTTP response body bytes received with the 
             given content type (excluding chunk headers) BEFORE the TX 
             performs its HTTP-level response body processing. HTTP response 
             headers and chunk headers/trailers are not counted, but any 
             compressed or uncompressed HTTP data is counted. Responses that 
             do not have a body (e.g. 304) are not counted."
        ::= { targetServerHTTPStatsEntry 29 }

tsHTTPStatsTargetBytesInFLASH OBJECT-TYPE
        SYNTAX     Counter64
        MAX-ACCESS read-only
        STATUS     current
        DESCRIPTION
            "Total number of HTTP response body bytes received with the 
             given content type (excluding chunk headers) BEFORE the TX 
             performs its HTTP-level response body processing. HTTP response 
             headers and chunk headers/trailers are not counted, but any 
             compressed or uncompressed HTTP data is counted. Responses that 
             do not have a body (e.g. 304) are not counted."
        ::= { targetServerHTTPStatsEntry 30 }

tsHTTPStatsTargetBytesInOthers OBJECT-TYPE
        SYNTAX     Counter64
        MAX-ACCESS read-only
        STATUS     current
        DESCRIPTION
            "Total number of HTTP response body bytes received with the 
             given content type (excluding chunk headers) BEFORE the TX 
             performs its HTTP-level response body processing. HTTP response 
             headers and chunk headers/trailers are not counted, but any 
             compressed or uncompressed HTTP data is counted. Responses that 
             do not have a body (e.g. 304) are not counted."
        ::= { targetServerHTTPStatsEntry 31 }

tsHTTPStatsTargetBytesOutGIF OBJECT-TYPE
        SYNTAX     Counter64
        MAX-ACCESS read-only
        STATUS     current
        DESCRIPTION
            "Total number of HTTP response body bytes with the given content 
             type that are remaining AFTER the TX performs its HTTP-level 
             response body processing (excluding chunk headers).  HTTP response 
             headers and chunk headers/trailers are not counted, but any
             compressed or uncompressed HTTP response data is counted.
             Responses that do not have a body (e.g. 304) are not counted."
        ::= { targetServerHTTPStatsEntry 32 }

tsHTTPStatsTargetBytesOutJPEG OBJECT-TYPE
        SYNTAX     Counter64
        MAX-ACCESS read-only
        STATUS     current
        DESCRIPTION
            "Total number of HTTP response body bytes with the given content 
             type that are remaining AFTER the TX performs its HTTP-level 
             response body processing (excluding chunk headers).  HTTP response 
             headers and chunk headers/trailers are not counted, but any
             compressed or uncompressed HTTP response data is counted.
             Responses that do not have a body (e.g. 304) are not counted."
        ::= { targetServerHTTPStatsEntry 33 }

tsHTTPStatsTargetBytesOutHTML OBJECT-TYPE
        SYNTAX     Counter64
        MAX-ACCESS read-only
        STATUS     current
        DESCRIPTION
            "Total number of HTTP response body bytes with the given content 
             type that are remaining AFTER the TX performs its HTTP-level 
             response body processing (excluding chunk headers).  HTTP response 
             headers and chunk headers/trailers are not counted, but any
             compressed or uncompressed HTTP response data is counted.
             Responses that do not have a body (e.g. 304) are not counted."
        ::= { targetServerHTTPStatsEntry 34 }

tsHTTPStatsTargetBytesOutCSS OBJECT-TYPE
        SYNTAX     Counter64
        MAX-ACCESS read-only
        STATUS     current
        DESCRIPTION
            "Total number of HTTP response body bytes with the given content 
             type that are remaining AFTER the TX performs its HTTP-level 
             response body processing (excluding chunk headers).  HTTP response 
             headers and chunk headers/trailers are not counted, but any
             compressed or uncompressed HTTP response data is counted.
             Responses that do not have a body (e.g. 304) are not counted."
        ::= { targetServerHTTPStatsEntry 35 }

tsHTTPStatsTargetBytesOutXML OBJECT-TYPE
        SYNTAX     Counter64
        MAX-ACCESS read-only
        STATUS     current
        DESCRIPTION
            "Total number of HTTP response body bytes with the given content 
             type that are remaining AFTER the TX performs its HTTP-level 
             response body processing (excluding chunk headers).  HTTP response 
             headers and chunk headers/trailers are not counted, but any
             compressed or uncompressed HTTP response data is counted.
             Responses that do not have a body (e.g. 304) are not counted."
        ::= { targetServerHTTPStatsEntry 36 }

tsHTTPStatsTargetBytesOutTEXT OBJECT-TYPE
        SYNTAX     Counter64
        MAX-ACCESS read-only
        STATUS     current
        DESCRIPTION
            "Total number of HTTP response body bytes with the given content 
             type that are remaining AFTER the TX performs its HTTP-level 
             response body processing (excluding chunk headers).  HTTP response 
             headers and chunk headers/trailers are not counted, but any
             compressed or uncompressed HTTP response data is counted.
             Responses that do not have a body (e.g. 304) are not counted."
        ::= { targetServerHTTPStatsEntry 37 }

tsHTTPStatsTargetBytesOutJAVASCRIPT OBJECT-TYPE
        SYNTAX     Counter64
        MAX-ACCESS read-only
        STATUS     current
        DESCRIPTION
            "Total number of HTTP response body bytes with the given content 
             type that are remaining AFTER the TX performs its HTTP-level 
             response body processing (excluding chunk headers).  HTTP response 
             headers and chunk headers/trailers are not counted, but any
             compressed or uncompressed HTTP response data is counted.
             Responses that do not have a body (e.g. 304) are not counted."
        ::= { targetServerHTTPStatsEntry 38 }

tsHTTPStatsTargetBytesOutFLASH OBJECT-TYPE
        SYNTAX     Counter64
        MAX-ACCESS read-only
        STATUS     current
        DESCRIPTION
            "Total number of HTTP response body bytes with the given content 
             type that are remaining AFTER the TX performs its HTTP-level 
             response body processing (excluding chunk headers).  HTTP response 
             headers and chunk headers/trailers are not counted, but any
             compressed or uncompressed HTTP response data is counted.
             Responses that do not have a body (e.g. 304) are not counted."
        ::= { targetServerHTTPStatsEntry 39 }

tsHTTPStatsTargetBytesOutOthers OBJECT-TYPE
        SYNTAX     Counter64
        MAX-ACCESS read-only
        STATUS     current
        DESCRIPTION
            "Total number of HTTP response body bytes with the given content 
             type that are remaining AFTER the TX performs its HTTP-level 
             response body processing (excluding chunk headers).  HTTP response 
             headers and chunk headers/trailers are not counted, but any
             compressed or uncompressed HTTP response data is counted.
             Responses that do not have a body (e.g. 304) are not counted."
        ::= { targetServerHTTPStatsEntry 40 }

tsHTTPStatsTargetResponseCode1xx OBJECT-TYPE
        SYNTAX     Counter64
        MAX-ACCESS read-only
        STATUS     current
        DESCRIPTION
            "The total number of HTTP 1xx response code."
        ::= { targetServerHTTPStatsEntry 41 }

tsHTTPStatsTargetResponseCode101 OBJECT-TYPE
        SYNTAX     Counter64
        MAX-ACCESS read-only
        STATUS     current
        DESCRIPTION
            "The total number of HTTP 101 response code."
        ::= { targetServerHTTPStatsEntry 42 }

tsHTTPStatsTargetResponseCode102 OBJECT-TYPE
        SYNTAX     Counter64
        MAX-ACCESS read-only
        STATUS     current
        DESCRIPTION
            "The total number of HTTP 102 response code."
        ::= { targetServerHTTPStatsEntry 43 }

tsHTTPStatsTargetResponseCode2xx OBJECT-TYPE
        SYNTAX     Counter64
        MAX-ACCESS read-only
        STATUS     current
        DESCRIPTION
            "The total number of HTTP 2xx response code."
        ::= { targetServerHTTPStatsEntry 44 }

tsHTTPStatsTargetResponseCode201 OBJECT-TYPE
        SYNTAX     Counter64
        MAX-ACCESS read-only
        STATUS     current
        DESCRIPTION
            "The total number of HTTP 201 response code."
        ::= { targetServerHTTPStatsEntry 45 }

tsHTTPStatsTargetResponseCode202 OBJECT-TYPE
        SYNTAX     Counter64
        MAX-ACCESS read-only
        STATUS     current
        DESCRIPTION
            "The total number of HTTP 202 response code."
        ::= { targetServerHTTPStatsEntry 46 }

tsHTTPStatsTargetResponseCode203 OBJECT-TYPE
        SYNTAX     Counter64
        MAX-ACCESS read-only
        STATUS     current
        DESCRIPTION
            "The total number of HTTP 203 response code."
        ::= { targetServerHTTPStatsEntry 47 }

tsHTTPStatsTargetResponseCode204 OBJECT-TYPE
        SYNTAX     Counter64
        MAX-ACCESS read-only
        STATUS     current
        DESCRIPTION
            "The total number of HTTP 204 response code."
        ::= { targetServerHTTPStatsEntry 48 }

tsHTTPStatsTargetResponseCode205 OBJECT-TYPE
        SYNTAX     Counter64
        MAX-ACCESS read-only
        STATUS     current
        DESCRIPTION
            "The total number of HTTP 205 response code."
        ::= { targetServerHTTPStatsEntry 49 }

tsHTTPStatsTargetResponseCode206 OBJECT-TYPE
        SYNTAX     Counter64
        MAX-ACCESS read-only
        STATUS     current
        DESCRIPTION
            "The total number of HTTP 206 response code."
        ::= { targetServerHTTPStatsEntry 50 }

tsHTTPStatsTargetResponseCode207 OBJECT-TYPE
        SYNTAX     Counter64
        MAX-ACCESS read-only
        STATUS     current
        DESCRIPTION
            "The total number of HTTP 207 response code."
        ::= { targetServerHTTPStatsEntry 51 }

tsHTTPStatsTargetResponseCode300 OBJECT-TYPE
        SYNTAX     Counter64
        MAX-ACCESS read-only
        STATUS     current
        DESCRIPTION
            "The total number of HTTP 300 response code."
        ::= { targetServerHTTPStatsEntry 52 }

tsHTTPStatsTargetResponseCode301 OBJECT-TYPE
        SYNTAX     Counter64
        MAX-ACCESS read-only
        STATUS     current
        DESCRIPTION
            "The total number of HTTP 301 response code."
        ::= { targetServerHTTPStatsEntry 53 }

tsHTTPStatsTargetResponseCode303 OBJECT-TYPE
        SYNTAX     Counter64
        MAX-ACCESS read-only
        STATUS     current
        DESCRIPTION
            "The total number of HTTP 303 response code."
        ::= { targetServerHTTPStatsEntry 54 }

tsHTTPStatsTargetResponseCode305 OBJECT-TYPE
        SYNTAX     Counter64
        MAX-ACCESS read-only
        STATUS     current
        DESCRIPTION
            "The total number of HTTP 305 response code."
        ::= { targetServerHTTPStatsEntry 55 }

tsHTTPStatsTargetResponseCode306 OBJECT-TYPE
        SYNTAX     Counter64
        MAX-ACCESS read-only
        STATUS     current
        DESCRIPTION
            "The total number of HTTP 300 response code."
        ::= { targetServerHTTPStatsEntry 56 }

tsHTTPStatsTargetResponseCode307 OBJECT-TYPE
        SYNTAX     Counter64
        MAX-ACCESS read-only
        STATUS     current
        DESCRIPTION
            "The total number of HTTP 307 response code."
        ::= { targetServerHTTPStatsEntry 57 }

tsHTTPStatsTargetResponseCode400 OBJECT-TYPE
        SYNTAX     Counter64
        MAX-ACCESS read-only
        STATUS     current
        DESCRIPTION
            "The total number of HTTP 400 response code."
        ::= { targetServerHTTPStatsEntry 58 }

tsHTTPStatsTargetResponseCode401 OBJECT-TYPE
        SYNTAX     Counter64
        MAX-ACCESS read-only
        STATUS     current
        DESCRIPTION
            "The total number of HTTP 401 response code."
        ::= { targetServerHTTPStatsEntry 59 }

tsHTTPStatsTargetResponseCode402 OBJECT-TYPE
        SYNTAX     Counter64
        MAX-ACCESS read-only
        STATUS     current
        DESCRIPTION
            "The total number of HTTP 402 response code."
        ::= { targetServerHTTPStatsEntry 60 }

tsHTTPStatsTargetResponseCode403 OBJECT-TYPE
        SYNTAX     Counter64
        MAX-ACCESS read-only
        STATUS     current
        DESCRIPTION
            "The total number of HTTP 403 response code."
        ::= { targetServerHTTPStatsEntry 61 }

tsHTTPStatsTargetResponseCode405 OBJECT-TYPE
        SYNTAX     Counter64
        MAX-ACCESS read-only
        STATUS     current
        DESCRIPTION
            "The total number of HTTP 405 response code."
        ::= { targetServerHTTPStatsEntry 62 }

tsHTTPStatsTargetResponseCode406 OBJECT-TYPE
        SYNTAX     Counter64
        MAX-ACCESS read-only
        STATUS     current
        DESCRIPTION
            "The total number of HTTP 406 response code."
        ::= { targetServerHTTPStatsEntry 63 }

tsHTTPStatsTargetResponseCode407 OBJECT-TYPE
        SYNTAX     Counter64
        MAX-ACCESS read-only
        STATUS     current
        DESCRIPTION
            "The total number of HTTP 407 response code."
        ::= { targetServerHTTPStatsEntry 64 }

tsHTTPStatsTargetResponseCode408 OBJECT-TYPE
        SYNTAX     Counter64
        MAX-ACCESS read-only
        STATUS     current
        DESCRIPTION
            "The total number of HTTP 408 response code."
        ::= { targetServerHTTPStatsEntry 65 }

tsHTTPStatsTargetResponseCode409 OBJECT-TYPE
        SYNTAX     Counter64
        MAX-ACCESS read-only
        STATUS     current
        DESCRIPTION
            "The total number of HTTP 409 response code."
        ::= { targetServerHTTPStatsEntry 66 }

tsHTTPStatsTargetResponseCode410 OBJECT-TYPE
        SYNTAX     Counter64
        MAX-ACCESS read-only
        STATUS     current
        DESCRIPTION
            "The total number of HTTP 410 response code."
        ::= { targetServerHTTPStatsEntry 67 }

tsHTTPStatsTargetResponseCode411 OBJECT-TYPE
        SYNTAX     Counter64
        MAX-ACCESS read-only
        STATUS     current
        DESCRIPTION
            "The total number of HTTP 411 response code."
        ::= { targetServerHTTPStatsEntry 68 }

tsHTTPStatsTargetResponseCode412 OBJECT-TYPE
        SYNTAX     Counter64
        MAX-ACCESS read-only
        STATUS     current
        DESCRIPTION
            "The total number of HTTP 412 response code."
        ::= { targetServerHTTPStatsEntry 69 }

tsHTTPStatsTargetResponseCode413 OBJECT-TYPE
        SYNTAX     Counter64
        MAX-ACCESS read-only
        STATUS     current
        DESCRIPTION
            "The total number of HTTP 413 response code."
        ::= { targetServerHTTPStatsEntry 70 }

tsHTTPStatsTargetResponseCode414 OBJECT-TYPE
        SYNTAX     Counter64
        MAX-ACCESS read-only
        STATUS     current
        DESCRIPTION
            "The total number of HTTP 414 response code."
        ::= { targetServerHTTPStatsEntry 71 }

tsHTTPStatsTargetResponseCode415 OBJECT-TYPE
        SYNTAX     Counter64
        MAX-ACCESS read-only
        STATUS     current
        DESCRIPTION
            "The total number of HTTP 415 response code."
        ::= { targetServerHTTPStatsEntry 72 }

tsHTTPStatsTargetResponseCode416 OBJECT-TYPE
        SYNTAX     Counter64
        MAX-ACCESS read-only
        STATUS     current
        DESCRIPTION
            "The total number of HTTP 416 response code."
        ::= { targetServerHTTPStatsEntry 73 }

tsHTTPStatsTargetResponseCode417 OBJECT-TYPE
        SYNTAX     Counter64
        MAX-ACCESS read-only
        STATUS     current
        DESCRIPTION
            "The total number of HTTP 417 response code."
        ::= { targetServerHTTPStatsEntry 74 }

tsHTTPStatsTargetResponseCode422 OBJECT-TYPE
        SYNTAX     Counter64
        MAX-ACCESS read-only
        STATUS     current
        DESCRIPTION
            "The total number of HTTP 422 response code."
        ::= { targetServerHTTPStatsEntry 75 }

tsHTTPStatsTargetResponseCode423 OBJECT-TYPE
        SYNTAX     Counter64
        MAX-ACCESS read-only
        STATUS     current
        DESCRIPTION
            "The total number of HTTP 423 response code."
        ::= { targetServerHTTPStatsEntry 76 }

tsHTTPStatsTargetResponseCode424 OBJECT-TYPE
        SYNTAX     Counter64
        MAX-ACCESS read-only
        STATUS     current
        DESCRIPTION
            "The total number of HTTP 424 response code."
        ::= { targetServerHTTPStatsEntry 77 }

tsHTTPStatsTargetResponseCode425 OBJECT-TYPE
        SYNTAX     Counter64
        MAX-ACCESS read-only
        STATUS     current
        DESCRIPTION
            "The total number of HTTP 425 response code."
        ::= { targetServerHTTPStatsEntry 78 }

tsHTTPStatsTargetResponseCode500 OBJECT-TYPE
        SYNTAX     Counter64
        MAX-ACCESS read-only
        STATUS     current
        DESCRIPTION
            "The total number of HTTP 500 response code."
        ::= { targetServerHTTPStatsEntry 79 }

tsHTTPStatsTargetResponseCode501 OBJECT-TYPE
        SYNTAX     Counter64
        MAX-ACCESS read-only
        STATUS     current
        DESCRIPTION
            "The total number of HTTP 501 response code."
        ::= { targetServerHTTPStatsEntry 80 }

tsHTTPStatsTargetResponseCode502 OBJECT-TYPE
        SYNTAX     Counter64
        MAX-ACCESS read-only
        STATUS     current
        DESCRIPTION
            "The total number of HTTP 502 response code."
        ::= { targetServerHTTPStatsEntry 81 }

tsHTTPStatsTargetResponseCode503 OBJECT-TYPE
        SYNTAX     Counter64
        MAX-ACCESS read-only
        STATUS     current
        DESCRIPTION
            "The total number of HTTP 503 response code."
        ::= { targetServerHTTPStatsEntry 82 }

tsHTTPStatsTargetResponseCode504 OBJECT-TYPE
        SYNTAX     Counter64
        MAX-ACCESS read-only
        STATUS     current
        DESCRIPTION
            "The total number of HTTP 504 response code."
        ::= { targetServerHTTPStatsEntry 83 }

tsHTTPStatsTargetResponseCode505 OBJECT-TYPE
        SYNTAX     Counter64
        MAX-ACCESS read-only
        STATUS     current
        DESCRIPTION
            "The total number of HTTP 505 response code."
        ::= { targetServerHTTPStatsEntry 84 }

tsHTTPStatsTargetResponseCode506 OBJECT-TYPE
        SYNTAX     Counter64
        MAX-ACCESS read-only
        STATUS     current
        DESCRIPTION
            "The total number of HTTP 506 response code."
        ::= { targetServerHTTPStatsEntry 85 }

tsHTTPStatsTargetResponseCode507 OBJECT-TYPE
        SYNTAX     Counter64
        MAX-ACCESS read-only
        STATUS     current
        DESCRIPTION
            "The total number of HTTP 507 response code."
        ::= { targetServerHTTPStatsEntry 86 }

tsHTTPStatsTargetContentXCOMPONENT OBJECT-TYPE
        SYNTAX     Counter64
        MAX-ACCESS read-only
        STATUS     current
        DESCRIPTION
            "The total number of responses with content type X-COMPONENT."
        ::= { targetServerHTTPStatsEntry 87 }

tsHTTPStatsTargetContentOCTETSTREAM OBJECT-TYPE
        SYNTAX     Counter64
        MAX-ACCESS read-only
        STATUS     current
        DESCRIPTION
            "The total number of responses with content type OCTET-STREAM."
        ::= { targetServerHTTPStatsEntry 88 }

tsHTTPStatsTargetContentMSWORD OBJECT-TYPE
        SYNTAX     Counter64
        MAX-ACCESS read-only
        STATUS     current
        DESCRIPTION
            "The total number of responses with content type MSWORD."
        ::= { targetServerHTTPStatsEntry 89 }

tsHTTPStatsTargetContentMSEXCEL OBJECT-TYPE
        SYNTAX     Counter64
        MAX-ACCESS read-only
        STATUS     current
        DESCRIPTION
            "The total number of responses with content type MSEXCEL."
        ::= { targetServerHTTPStatsEntry 90 }

tsHTTPStatsTargetContentMSPOWERPOINT OBJECT-TYPE
        SYNTAX     Counter64
        MAX-ACCESS read-only
        STATUS     current
        DESCRIPTION
            "The total number of responses with content type MSPOWERPOINT."
        ::= { targetServerHTTPStatsEntry 91 }

tsHTTPStatsTargetContentCUSTOM1 OBJECT-TYPE
        SYNTAX     Counter64
        MAX-ACCESS read-only
        STATUS     current
        DESCRIPTION
            "The total number of responses with content type CUSTOM1."
        ::= { targetServerHTTPStatsEntry 92 }

tsHTTPStatsTargetContentCUSTOM2 OBJECT-TYPE
        SYNTAX     Counter64
        MAX-ACCESS read-only
        STATUS     current
        DESCRIPTION
            "The total number of responses with content type CUSTOM2."
        ::= { targetServerHTTPStatsEntry 93 }

tsHTTPStatsTargetContentCUSTOM3 OBJECT-TYPE
        SYNTAX     Counter64
        MAX-ACCESS read-only
        STATUS     current
        DESCRIPTION
            "The total number of responses with content type CUSTOM3."
        ::= { targetServerHTTPStatsEntry 94 }

tsHTTPStatsTargetBytesInXCOMPONENT OBJECT-TYPE
        SYNTAX     Counter64
        MAX-ACCESS read-only
        STATUS     current
        DESCRIPTION
            "Total number of HTTP response body bytes received with the 
             given content type (excluding chunk headers) BEFORE the TX 
             performs its HTTP-level response body processing. HTTP response 
             headers and chunk headers/trailers are not counted, but any 
             compressed or uncompressed HTTP data is counted. Responses that 
             do not have a body (e.g. 304) are not counted."
        ::= { targetServerHTTPStatsEntry 95 }

tsHTTPStatsTargetBytesInOCTETSTREAM OBJECT-TYPE
        SYNTAX     Counter64
        MAX-ACCESS read-only
        STATUS     current
        DESCRIPTION
            "Total number of HTTP response body bytes received with the 
             given content type (excluding chunk headers) BEFORE the TX 
             performs its HTTP-level response body processing. HTTP response 
             headers and chunk headers/trailers are not counted, but any 
             compressed or uncompressed HTTP data is counted. Responses that 
             do not have a body (e.g. 304) are not counted."
        ::= { targetServerHTTPStatsEntry 96 }

tsHTTPStatsTargetBytesInMSWORD OBJECT-TYPE
        SYNTAX     Counter64
        MAX-ACCESS read-only
        STATUS     current
        DESCRIPTION
            "Total number of HTTP response body bytes received with the 
             given content type (excluding chunk headers) BEFORE the TX 
             performs its HTTP-level response body processing. HTTP response 
             headers and chunk headers/trailers are not counted, but any 
             compressed or uncompressed HTTP data is counted. Responses that 
             do not have a body (e.g. 304) are not counted."
        ::= { targetServerHTTPStatsEntry 97 }

tsHTTPStatsTargetBytesInMSEXCEL OBJECT-TYPE
        SYNTAX     Counter64
        MAX-ACCESS read-only
        STATUS     current
        DESCRIPTION
            "Total number of HTTP response body bytes received with the 
             given content type (excluding chunk headers) BEFORE the TX 
             performs its HTTP-level response body processing. HTTP response 
             headers and chunk headers/trailers are not counted, but any 
             compressed or uncompressed HTTP data is counted. Responses that 
             do not have a body (e.g. 304) are not counted."
        ::= { targetServerHTTPStatsEntry 98 }

tsHTTPStatsTargetBytesInMSPOWERPOINT OBJECT-TYPE
        SYNTAX     Counter64
        MAX-ACCESS read-only
        STATUS     current
        DESCRIPTION
            "Total number of HTTP response body bytes received with the 
             given content type (excluding chunk headers) BEFORE the TX 
             performs its HTTP-level response body processing. HTTP response 
             headers and chunk headers/trailers are not counted, but any 
             compressed or uncompressed HTTP data is counted. Responses that 
             do not have a body (e.g. 304) are not counted."
        ::= { targetServerHTTPStatsEntry 99 }

tsHTTPStatsTargetBytesInCUSTOM1 OBJECT-TYPE
        SYNTAX     Counter64
        MAX-ACCESS read-only
        STATUS     current
        DESCRIPTION
            "Total number of HTTP response body bytes received with the 
             given content type (excluding chunk headers) BEFORE the TX 
             performs its HTTP-level response body processing. HTTP response 
             headers and chunk headers/trailers are not counted, but any 
             compressed or uncompressed HTTP data is counted. Responses that 
             do not have a body (e.g. 304) are not counted."
        ::= { targetServerHTTPStatsEntry 100 }

tsHTTPStatsTargetBytesInCUSTOM2 OBJECT-TYPE
        SYNTAX     Counter64
        MAX-ACCESS read-only
        STATUS     current
        DESCRIPTION
            "Total number of HTTP response body bytes received with the 
             given content type (excluding chunk headers) BEFORE the TX 
             performs its HTTP-level response body processing. HTTP response 
             headers and chunk headers/trailers are not counted, but any 
             compressed or uncompressed HTTP data is counted. Responses that 
             do not have a body (e.g. 304) are not counted."
        ::= { targetServerHTTPStatsEntry 101 }

tsHTTPStatsTargetBytesInCUSTOM3 OBJECT-TYPE
        SYNTAX     Counter64
        MAX-ACCESS read-only
        STATUS     current
        DESCRIPTION
            "Total number of HTTP response body bytes received with the 
             given content type (excluding chunk headers) BEFORE the TX 
             performs its HTTP-level response body processing. HTTP response 
             headers and chunk headers/trailers are not counted, but any 
             compressed or uncompressed HTTP data is counted. Responses that 
             do not have a body (e.g. 304) are not counted."
        ::= { targetServerHTTPStatsEntry 102 }

tsHTTPStatsTargetBytesOutXCOMPONENT OBJECT-TYPE
        SYNTAX     Counter64
        MAX-ACCESS read-only
        STATUS     current
        DESCRIPTION
            "Total number of HTTP response body bytes with the given content 
             type that are remaining AFTER the TX performs its HTTP-level 
             response body processing (excluding chunk headers).  HTTP response 
             headers and chunk headers/trailers are not counted, but any
             compressed or uncompressed HTTP response data is counted.
             Responses that do not have a body (e.g. 304) are not counted."
        ::= { targetServerHTTPStatsEntry 103 }

tsHTTPStatsTargetBytesOutOCTETSTREAM OBJECT-TYPE
        SYNTAX     Counter64
        MAX-ACCESS read-only
        STATUS     current
        DESCRIPTION
            "Total number of HTTP response body bytes with the given content 
             type that are remaining AFTER the TX performs its HTTP-level 
             response body processing (excluding chunk headers).  HTTP response 
             headers and chunk headers/trailers are not counted, but any
             compressed or uncompressed HTTP response data is counted.
             Responses that do not have a body (e.g. 304) are not counted."
        ::= { targetServerHTTPStatsEntry 104 }

tsHTTPStatsTargetBytesOutMSWORD OBJECT-TYPE
        SYNTAX     Counter64
        MAX-ACCESS read-only
        STATUS     current
        DESCRIPTION
            "Total number of HTTP response body bytes with the given content 
             type that are remaining AFTER the TX performs its HTTP-level 
             response body processing (excluding chunk headers).  HTTP response 
             headers and chunk headers/trailers are not counted, but any
             compressed or uncompressed HTTP response data is counted.
             Responses that do not have a body (e.g. 304) are not counted."
        ::= { targetServerHTTPStatsEntry 105 }

tsHTTPStatsTargetBytesOutMSEXCEL OBJECT-TYPE
        SYNTAX     Counter64
        MAX-ACCESS read-only
        STATUS     current
        DESCRIPTION
            "Total number of HTTP response body bytes with the given content 
             type that are remaining AFTER the TX performs its HTTP-level 
             response body processing (excluding chunk headers).  HTTP response 
             headers and chunk headers/trailers are not counted, but any
             compressed or uncompressed HTTP response data is counted.
             Responses that do not have a body (e.g. 304) are not counted."
        ::= { targetServerHTTPStatsEntry 106 }

tsHTTPStatsTargetBytesOutMSPOWERPOINT OBJECT-TYPE
        SYNTAX     Counter64
        MAX-ACCESS read-only
        STATUS     current
        DESCRIPTION
            "Total number of HTTP response body bytes with the given content 
             type that are remaining AFTER the TX performs its HTTP-level 
             response body processing (excluding chunk headers).  HTTP response 
             headers and chunk headers/trailers are not counted, but any
             compressed or uncompressed HTTP response data is counted.
             Responses that do not have a body (e.g. 304) are not counted."
        ::= { targetServerHTTPStatsEntry 107 }

tsHTTPStatsTargetBytesOutCUSTOM1 OBJECT-TYPE
        SYNTAX     Counter64
        MAX-ACCESS read-only
        STATUS     current
        DESCRIPTION
            "Total number of HTTP response body bytes with the given content 
             type that are remaining AFTER the TX performs its HTTP-level 
             response body processing (excluding chunk headers).  HTTP response 
             headers and chunk headers/trailers are not counted, but any
             compressed or uncompressed HTTP response data is counted.
             Responses that do not have a body (e.g. 304) are not counted."
        ::= { targetServerHTTPStatsEntry 108 }

tsHTTPStatsTargetBytesOutCUSTOM2 OBJECT-TYPE
        SYNTAX     Counter64
        MAX-ACCESS read-only
        STATUS     current
        DESCRIPTION
            "Total number of HTTP response body bytes with the given content 
             type that are remaining AFTER the TX performs its HTTP-level 
             response body processing (excluding chunk headers).  HTTP response 
             headers and chunk headers/trailers are not counted, but any
             compressed or uncompressed HTTP response data is counted.
             Responses that do not have a body (e.g. 304) are not counted."
        ::= { targetServerHTTPStatsEntry 109 }

tsHTTPStatsTargetBytesOutCUSTOM3 OBJECT-TYPE
        SYNTAX     Counter64
        MAX-ACCESS read-only
        STATUS     current
        DESCRIPTION
            "Total number of HTTP response body bytes with the given content 
             type that are remaining AFTER the TX performs its HTTP-level 
             response body processing (excluding chunk headers).  HTTP response 
             headers and chunk headers/trailers are not counted, but any
             compressed or uncompressed HTTP response data is counted.
             Responses that do not have a body (e.g. 304) are not counted."
        ::= { targetServerHTTPStatsEntry 110 }


---------------------------------------------------------------------------
-- SSL Statistics per targetServer
---------------------------------------------------------------------------
targetServerSSLStatsTable OBJECT-TYPE
        SYNTAX     SEQUENCE OF TargetServerSSLStatsEntry
        MAX-ACCESS not-accessible
        STATUS     current
        DESCRIPTION
            "The (conceptual) table listing the targetServers SSL stats."
        ::= { targetServerStats 3 }

targetServerSSLStatsEntry OBJECT-TYPE
        SYNTAX     TargetServerSSLStatsEntry
        MAX-ACCESS not-accessible
        STATUS     current
        DESCRIPTION
            "An entry (conceptual row) in the targetServerSSLStats table."
        INDEX      { tsSSLStatsIndex }
        ::= { targetServerSSLStatsTable 1 }

TargetServerSSLStatsEntry ::=
        SEQUENCE {
        tsSSLStatsIndex 
           Integer32,
        tsSSLStatsCluster
           DisplayString,
        tsSSLStatsPhysicalServer 
           DisplayString,
        tsSSLStatsClusterType 
           INTEGER,
        tsSSLStatsNewSessions 
           Counter64,
        tsSSLStatsReusedSessions 
           Counter64,
        tsSSLStatsStrongEncryption 
           Counter64,
        tsSSLStatsExportEncryption 
           Counter64,
        tsSSLStatsSSLv2Req 
           Counter64,
        tsSSLStatsSSLv3Req 
           Counter64,
        tsSSLStatsTLSv1Req 
           Counter64,
        tsSSLStatsOtherSSLVersionReq 
           Counter64
        }

tsSSLStatsIndex OBJECT-TYPE
        SYNTAX     Integer32 (0..2147483647)
        MAX-ACCESS not-accessible
        STATUS     current
        DESCRIPTION
            "The TargetServer Index"
        ::= { targetServerSSLStatsEntry 1 }

tsSSLStatsCluster OBJECT-TYPE
        SYNTAX     DisplayString
        MAX-ACCESS read-only
        STATUS     current
        DESCRIPTION
            "The cluster to which this physical server is bound."
        ::= { targetServerSSLStatsEntry 2 }

tsSSLStatsPhysicalServer OBJECT-TYPE
        SYNTAX     DisplayString
        MAX-ACCESS read-only
        STATUS     current
        DESCRIPTION
            "The physical server's IP address and port ."
        ::= { targetServerSSLStatsEntry 3 }

tsSSLStatsClusterType OBJECT-TYPE
        SYNTAX     INTEGER { global(0), admin(1), http(2), forwarder(3), redirector(4), comm(8), healthcheck(9), redirect(10) }
        MAX-ACCESS read-only
        STATUS     current
        DESCRIPTION
            "The cluster type ( HTTP | FORWARDER | REDIRECTOR | ..... )."
        ::= { targetServerSSLStatsEntry 4 }

tsSSLStatsNewSessions OBJECT-TYPE
        SYNTAX     Counter64
        MAX-ACCESS read-only
        STATUS     current
        DESCRIPTION
            "The total number of new sessions on target side."
        ::= { targetServerSSLStatsEntry 5 }

tsSSLStatsReusedSessions OBJECT-TYPE
        SYNTAX     Counter64
        MAX-ACCESS read-only
        STATUS     current
        DESCRIPTION
            "The total number of reused sessions on target side."
        ::= { targetServerSSLStatsEntry 6 }

tsSSLStatsStrongEncryption OBJECT-TYPE
        SYNTAX     Counter64
        MAX-ACCESS read-only
        STATUS     current
        DESCRIPTION
            "The total number of SSL request using strong encryption on target side."
        ::= { targetServerSSLStatsEntry 7 }

tsSSLStatsExportEncryption OBJECT-TYPE
        SYNTAX     Counter64
        MAX-ACCESS read-only
        STATUS     current
        DESCRIPTION
            "The total number of SSL request using export encryption on target side."
        ::= { targetServerSSLStatsEntry 8 }

tsSSLStatsSSLv2Req OBJECT-TYPE
        SYNTAX     Counter64
        MAX-ACCESS read-only
        STATUS     current
        DESCRIPTION
            "The total number of SSLv3 Requests on target side."
        ::= { targetServerSSLStatsEntry 9 }

tsSSLStatsSSLv3Req OBJECT-TYPE
        SYNTAX     Counter64
        MAX-ACCESS read-only
        STATUS     current
        DESCRIPTION
            "The total number of SSLv3 Requests on target side."
        ::= { targetServerSSLStatsEntry 10 }

tsSSLStatsTLSv1Req OBJECT-TYPE
        SYNTAX     Counter64
        MAX-ACCESS read-only
        STATUS     current
        DESCRIPTION
            "The total number of TLSv1 Requests on target side."
        ::= { targetServerSSLStatsEntry 11 }

tsSSLStatsOtherSSLVersionReq OBJECT-TYPE
        SYNTAX     Counter64
        MAX-ACCESS read-only
        STATUS     deprecated
        DESCRIPTION
            "The total number of OtherSSLVersionReq Requests on target side."
        ::= { targetServerSSLStatsEntry 12 }

---------------------------------------------------------------------------
-- Target Server health check table.
---------------------------------------------------------------------------
targetServerHealthTable OBJECT-TYPE
        SYNTAX     SEQUENCE OF TargetServerHealthEntry
        MAX-ACCESS not-accessible
        STATUS     current
        DESCRIPTION
            "The (conceptual) table listing the targetServers health check status."
        ::= { targetServerStats 4 }

targetServerHealthEntry OBJECT-TYPE
        SYNTAX     TargetServerHealthEntry
        MAX-ACCESS not-accessible
        STATUS     current
        DESCRIPTION
            "An entry (conceptual row) in the targetServerHealth table."
        INDEX      { tsHealthIndex }
        ::= { targetServerHealthTable 1 }

TargetServerHealthEntry ::=
        SEQUENCE {
        tsHealthIndex 
           Integer32,
        tsHealthClusterName
           DisplayString,
        tsHealthPhysicalServer 
           DisplayString,
        tsHealthStatus
           INTEGER,
        tsHealthDetail
           INTEGER
        }

tsHealthIndex OBJECT-TYPE
        SYNTAX     Integer32 ( 0..2147483647 )
        MAX-ACCESS not-accessible
        STATUS     current
        DESCRIPTION
            "The auxiliary variable used for identifying instances of
             the columnar objects in the target server table."
        ::= { targetServerHealthEntry 1 }

tsHealthClusterName OBJECT-TYPE
        SYNTAX     DisplayString
        MAX-ACCESS read-only
        STATUS     current
        DESCRIPTION
            "The cluster to which this physical server is bound."
        ::= { targetServerHealthEntry 2 }

tsHealthPhysicalServer OBJECT-TYPE
        SYNTAX     DisplayString
        MAX-ACCESS read-only
        STATUS     current
        DESCRIPTION
            "The physical server's IP address and port ."
        ::= { targetServerHealthEntry 3 }

tsHealthStatus OBJECT-TYPE
        SYNTAX     INTEGER { down(0), up(1) }
        MAX-ACCESS read-only
        STATUS     current
        DESCRIPTION
            "Indicates the current health of this Target Server."
        ::= { targetServerHealthEntry 5 }

tsHealthDetail OBJECT-TYPE
        SYNTAX     INTEGER { noReason(-1), unknownReason(0), connectionRefused(1), connectionTimeout(2), connectionUnknown(3), transportLayerProtocolClosed(4), transportLayerProtocolFailure(5), transportLayerProtocolTimeout(6), responseTimeout (7), returnCodeMismatch(8), responseSizeMismatch(9), responseStringMismatch(10), corruptReply(11), unknownLayer7Reason(12), pendingUp(13), up(14) , softPaused(15), hardPaused(16)}
        MAX-ACCESS read-only
        STATUS     current
        DESCRIPTION
            "Indicates the detail relating to the current health of this Target Server."
        ::= { targetServerHealthEntry 6 }


---------------------------------------------------------------------------
-- GSLB Statistics
---------------------------------------------------------------------------
gslbStats OBJECT IDENTIFIER ::= { dxStats 6 }

gslbAgentStats OBJECT IDENTIFIER ::= { gslbStats 1 }

gslbAgentStatsMetricsRequestsReceived OBJECT-TYPE
        SYNTAX     Counter64
        MAX-ACCESS read-only
        STATUS     current
        DESCRIPTION
            "Metrics Requests the GSLB Agent has received."
        ::= { gslbAgentStats 1 }

gslbAgentStatsMetricsRepliesSent OBJECT-TYPE
        SYNTAX     Counter64
        MAX-ACCESS read-only
        STATUS     current
        DESCRIPTION
            "Metrics Replies the GSLB Agent has sent."
        ::= { gslbAgentStats 2 }

gslbAgentStatsRTTRequestsReceived OBJECT-TYPE
        SYNTAX     Counter64
        MAX-ACCESS read-only
        STATUS     current
        DESCRIPTION
            "RTT Requests the GSLB Agent has received."
        ::= { gslbAgentStats 3 }

gslbAgentStatsRTTRepliesSent OBJECT-TYPE
        SYNTAX     Counter64
        MAX-ACCESS read-only
        STATUS     current
        DESCRIPTION
            "RTT Replies the GSLB Agent has sent."
        ::= { gslbAgentStats 4 }

gslbRemoteNodeStats OBJECT IDENTIFIER ::= { gslbStats 2 }

gslbRemoteNodeStatsTable OBJECT-TYPE
        SYNTAX     SEQUENCE OF GslbRemoteNodeStatsEntry
        MAX-ACCESS not-accessible
        STATUS     current
        DESCRIPTION
            "The (conceptual) table listing all the GSLB RemoteNodes."
        ::= { gslbRemoteNodeStats 1 }

gslbRemoteNodeStatsEntry OBJECT-TYPE
        SYNTAX     GslbRemoteNodeStatsEntry
        MAX-ACCESS not-accessible
        STATUS     current
        DESCRIPTION
            "An entry (conceptual row) in the gslbRemoteNodeStatsTable."
        INDEX      { gslbRemoteNodeUUID }
        ::= { gslbRemoteNodeStatsTable 1 }

GslbRemoteNodeStatsEntry ::=
		SEQUENCE {
			gslbRemoteNodeUUID
				DisplayString,

			gslbRemoteNodeName
				DisplayString,

			gslbRemoteNodeStatus
				INTEGER,

			gslbRemoteNodeRTTRequestsSent
				Counter64,

			gslbRemoteNodeRTTRequestsReplies
				Counter64,

			gslbRemoteNodeRTTRequestsErrors
				Counter64,

			gslbRemoteNodeMetricsRequestsSent
				Counter64,

			gslbRemoteNodeMetricsRequestReplies
				Counter64,

			gslbRemoteNodeMetricsErrors
				Counter64

		}

gslbRemoteNodeUUID OBJECT-TYPE
        SYNTAX     DisplayString
        MAX-ACCESS read-only
        STATUS     current
        DESCRIPTION
            "The unique UUID of a RemoteNode, used to index into the table."
        ::= { gslbRemoteNodeStatsEntry 1 }

gslbRemoteNodeName OBJECT-TYPE
        SYNTAX     DisplayString
        MAX-ACCESS read-only
        STATUS     current
        DESCRIPTION
            "The name of this RemoteNode."
        ::= { gslbRemoteNodeStatsEntry 2 }

gslbRemoteNodeStatus OBJECT-TYPE
        SYNTAX     INTEGER { down(0), up(1) }
        MAX-ACCESS read-only
        STATUS     current
        DESCRIPTION
            "The status of this remotenode, down (0) or up (1)."
        ::= { gslbRemoteNodeStatsEntry 3 }

gslbRemoteNodeRTTRequestsSent OBJECT-TYPE
        SYNTAX     Counter64
        MAX-ACCESS read-only
        STATUS     current
        DESCRIPTION
            "RTT requests sent to this remotenode."
        ::= { gslbRemoteNodeStatsEntry 4 }

gslbRemoteNodeRTTRequestsReplies OBJECT-TYPE
        SYNTAX     Counter64
        MAX-ACCESS read-only
        STATUS     current
        DESCRIPTION
            "RTT replies received from this remotenode."
        ::= { gslbRemoteNodeStatsEntry 5 }

gslbRemoteNodeRTTRequestsErrors OBJECT-TYPE
        SYNTAX     Counter64
        MAX-ACCESS read-only
        STATUS     current
        DESCRIPTION
            "RTT request errors received from this remotenode."
        ::= { gslbRemoteNodeStatsEntry 6 }

gslbRemoteNodeMetricsRequestsSent OBJECT-TYPE
        SYNTAX     Counter64
        MAX-ACCESS read-only
        STATUS     current
        DESCRIPTION
            "Metrics requests sent to this remotenode."
        ::= { gslbRemoteNodeStatsEntry 7 }

gslbRemoteNodeMetricsRequestReplies OBJECT-TYPE
        SYNTAX     Counter64
        MAX-ACCESS read-only
        STATUS     current
        DESCRIPTION
            "Metrics replies received from this remotenode."
        ::= { gslbRemoteNodeStatsEntry 8 }

gslbRemoteNodeMetricsErrors OBJECT-TYPE
        SYNTAX     Counter64
        MAX-ACCESS read-only
        STATUS     current
        DESCRIPTION
            "Metrics errors recieved from this remotenode."
        ::= { gslbRemoteNodeStatsEntry 9 }

gslbResolverStats OBJECT IDENTIFIER ::= { gslbStats 3 }

gslbResolverStatsTable OBJECT-TYPE
        SYNTAX     SEQUENCE OF GslbResolverStatsEntry
        MAX-ACCESS not-accessible
        STATUS     current
        DESCRIPTION
            "The (conceptual) table listing all the GSLB Resolvers."
        ::= { gslbResolverStats 1 }

gslbResolverStatsEntry OBJECT-TYPE
        SYNTAX     GslbResolverStatsEntry
        MAX-ACCESS not-accessible
        STATUS     current
        DESCRIPTION
            "An entry (conceptual row) in the gslbResolverTable."
        INDEX      { gslbResolverUUID }
        ::= { gslbResolverStatsTable 1 }

GslbResolverStatsEntry ::=
		SEQUENCE {
			gslbResolverUUID
				DisplayString,

			gslbResolverName
				DisplayString,

			gslbResolverUDPRequests
				Counter64,

			gslbResolverUDPReplies
				Counter64,

			gslbResolverUDPForwards
				Counter64,

			gslbResolverUDPForwardReplies
				Counter64,

			gslbResolverUDPErrors
				Counter64,

			gslbResolverTCPRequests
				Counter64,

			gslbResolverTCPReplies
				Counter64,

			gslbResolverTCPForwards
				Counter64,

			gslbResolverTCPForwardReplies
				Counter64,

			gslbResolverTCPErrors
				Counter64,

			gslbResolverQueryTypeA
				Counter64,

			gslbResolverQueryTypeNS
				Counter64,

			gslbResolverQueryTypeCNAME
				Counter64,

			gslbResolverQueryTypeSOA
				Counter64,

			gslbResolverQueryTypePTR
				Counter64,

			gslbResolverQueryTypeMX
				Counter64,

			gslbResolverQueryTypeOther
				Counter64

		}

gslbResolverUUID OBJECT-TYPE
        SYNTAX     DisplayString
        MAX-ACCESS read-only
        STATUS     current
        DESCRIPTION
            "The unique UUID of a Resolver, used to index into the table."
        ::= { gslbResolverStatsEntry 1 }

gslbResolverName OBJECT-TYPE
        SYNTAX     DisplayString
        MAX-ACCESS read-only
        STATUS     current
        DESCRIPTION
            "The name of this Resolver."
        ::= { gslbResolverStatsEntry 2 }

gslbResolverUDPRequests OBJECT-TYPE
        SYNTAX     Counter64
        MAX-ACCESS read-only
        STATUS     current
        DESCRIPTION
            "The count of UDP DNS requests this resolver has received."
        ::= { gslbResolverStatsEntry 3 }

gslbResolverUDPReplies OBJECT-TYPE
        SYNTAX     Counter64
        MAX-ACCESS read-only
        STATUS     current
        DESCRIPTION
            "The count of UDP DNS replies this resolver has sent."
        ::= { gslbResolverStatsEntry 4 }

gslbResolverUDPForwards OBJECT-TYPE
        SYNTAX     Counter64
        MAX-ACCESS read-only
        STATUS     current
        DESCRIPTION
            "The count of UDP DNS requests this resolver has forwarded to
             the target DNS server."
        ::= { gslbResolverStatsEntry 5 }

gslbResolverUDPForwardReplies OBJECT-TYPE
        SYNTAX     Counter64
        MAX-ACCESS read-only
        STATUS     current
        DESCRIPTION
            "The count of UDP DNS replies this resolver received from the
             target DNS server."
        ::= { gslbResolverStatsEntry 6 }

gslbResolverUDPErrors OBJECT-TYPE
        SYNTAX     Counter64
        MAX-ACCESS read-only
        STATUS     current
        DESCRIPTION
            "The count of UDP DNS error messages this resolver has sent."
        ::= { gslbResolverStatsEntry 7 }

gslbResolverTCPRequests OBJECT-TYPE
        SYNTAX     Counter64
        MAX-ACCESS read-only
        STATUS     current
        DESCRIPTION
            "The count of TCP DNS requests this resolver has received."
        ::= { gslbResolverStatsEntry 8 }

gslbResolverTCPReplies OBJECT-TYPE
        SYNTAX     Counter64
        MAX-ACCESS read-only
        STATUS     current
        DESCRIPTION
            "The count of TCP DNS replies this resolver has sent."
        ::= { gslbResolverStatsEntry 9 }

gslbResolverTCPForwards OBJECT-TYPE
        SYNTAX     Counter64
        MAX-ACCESS read-only
        STATUS     current
        DESCRIPTION
            "The count of TCP DNS requests this resolver has forwarded to
             the target DNS server."
        ::= { gslbResolverStatsEntry 10 }

gslbResolverTCPForwardReplies OBJECT-TYPE
        SYNTAX     Counter64
        MAX-ACCESS read-only
        STATUS     current
        DESCRIPTION
            "The count of TCP DNS replies this resolver received from the
             target DNS server."
        ::= { gslbResolverStatsEntry 11 }

gslbResolverTCPErrors OBJECT-TYPE
        SYNTAX     Counter64
        MAX-ACCESS read-only
        STATUS     current
        DESCRIPTION
            "The count of TCP DNS error messages this resolver has sent."
        ::= { gslbResolverStatsEntry 12 }

gslbResolverQueryTypeA OBJECT-TYPE
        SYNTAX     Counter64
        MAX-ACCESS read-only
        STATUS     current
        DESCRIPTION
            "The count of DNS A record requests this resolver has received."
        ::= { gslbResolverStatsEntry 13 }

gslbResolverQueryTypeNS OBJECT-TYPE
        SYNTAX     Counter64
        MAX-ACCESS read-only
        STATUS     current
        DESCRIPTION
            "The count of DNS NS record requests this resolver has received."
        ::= { gslbResolverStatsEntry 14 }

gslbResolverQueryTypeCNAME OBJECT-TYPE
        SYNTAX     Counter64
        MAX-ACCESS read-only
        STATUS     current
        DESCRIPTION
            "The count of DNS CNAME record requests this resolver has received."
        ::= { gslbResolverStatsEntry 15 }

gslbResolverQueryTypeSOA OBJECT-TYPE
        SYNTAX     Counter64
        MAX-ACCESS read-only
        STATUS     current
        DESCRIPTION
            "The count of DNS SOA record requests this resolver has received."
        ::= { gslbResolverStatsEntry 16 }

gslbResolverQueryTypePTR OBJECT-TYPE
        SYNTAX     Counter64
        MAX-ACCESS read-only
        STATUS     current
        DESCRIPTION
            "The count of DNS PTR record requests this resolver has received."
        ::= { gslbResolverStatsEntry 17 }

gslbResolverQueryTypeMX OBJECT-TYPE
        SYNTAX     Counter64
        MAX-ACCESS read-only
        STATUS     current
        DESCRIPTION
            "The count of DNS MX record requests this resolver has received."
        ::= { gslbResolverStatsEntry 18 }

gslbResolverQueryTypeOther OBJECT-TYPE
        SYNTAX     Counter64
        MAX-ACCESS read-only
        STATUS     current
        DESCRIPTION
            "The count of other DNS record requests this resolver has received."
        ::= { gslbResolverStatsEntry 19 }

gslbGroupStats OBJECT IDENTIFIER ::= { gslbStats 4 }

gslbGroupStatsTable OBJECT-TYPE
        SYNTAX     SEQUENCE OF GslbGroupStatsEntry
        MAX-ACCESS not-accessible
        STATUS     current
        DESCRIPTION
            "The (conceptual) table listing all the GSLB Resolver Groups."
        ::= { gslbGroupStats 1 }

gslbGroupStatsEntry OBJECT-TYPE
        SYNTAX     GslbGroupStatsEntry
        MAX-ACCESS not-accessible
        STATUS     current
        DESCRIPTION
            "An entry (conceptual row) in the gslbGroupStatsTable."
        INDEX      { gslbGroupResolverUUID, gslbGroupUUID }
        ::= { gslbGroupStatsTable 1 }

GslbGroupStatsEntry ::=
		SEQUENCE {
			gslbGroupResolverUUID
				DisplayString,

			gslbGroupUUID
				DisplayString,

			gslbGroupResolverName
				DisplayString,

			gslbGroupName
				DisplayString,

			gslbGroupRequests
				Counter64,

			gslbGroupRepliesNormal
				Counter64,

			gslbGroupRepliesFailIP
				Counter64,

			gslbGroupRepliesEmpty
				Counter64,

			gslbGroupRepliesTotal
				Counter64,

			gslbGroupRepliesErrors
				Counter64,

			gslbGroupStickyTableEntries
				Counter64

	}

gslbGroupResolverUUID OBJECT-TYPE
        SYNTAX     DisplayString
        MAX-ACCESS read-only
        STATUS     current
        DESCRIPTION
            "The UUID of the Resolver this group belongs to, also used to index into the table."
        ::= { gslbGroupStatsEntry 1 }

gslbGroupUUID OBJECT-TYPE
        SYNTAX     DisplayString
        MAX-ACCESS read-only
        STATUS     current
        DESCRIPTION
            "The unique UUID of a ResolverGroup, used to index into the table."
        ::= { gslbGroupStatsEntry 2 }

gslbGroupResolverName OBJECT-TYPE
        SYNTAX     DisplayString
        MAX-ACCESS read-only
        STATUS     current
        DESCRIPTION
            "The name of the Resolver this group belongs to, provided for display purposes."
        ::= { gslbGroupStatsEntry 3 }

gslbGroupName OBJECT-TYPE
        SYNTAX     DisplayString
        MAX-ACCESS read-only
        STATUS     current
        DESCRIPTION
            "The name of the group."
        ::= { gslbGroupStatsEntry 4 }

gslbGroupRequests OBJECT-TYPE
        SYNTAX     Counter64
        MAX-ACCESS read-only
        STATUS     current
        DESCRIPTION
            "The count of DNS requests handled by this group."
        ::= { gslbGroupStatsEntry 5 }

gslbGroupRepliesNormal OBJECT-TYPE
        SYNTAX     Counter64
        MAX-ACCESS read-only
        STATUS     current
        DESCRIPTION
            "The count of DNS replies generated by this group filled with
			load-balanced hosts."
        ::= { gslbGroupStatsEntry 6 }

gslbGroupRepliesFailIP OBJECT-TYPE
        SYNTAX     Counter64
        MAX-ACCESS read-only
        STATUS     current
        DESCRIPTION
            "The count of DNS replies generated by this group filled with
			the FailIP."
        ::= { gslbGroupStatsEntry 7 }

gslbGroupRepliesEmpty OBJECT-TYPE
        SYNTAX     Counter64
        MAX-ACCESS read-only
        STATUS     current
        DESCRIPTION
            "The count of DNS replies generated by this group containing
			an empty record."
        ::= { gslbGroupStatsEntry 8 }

gslbGroupRepliesTotal OBJECT-TYPE
        SYNTAX     Counter64
        MAX-ACCESS read-only
        STATUS     current
        DESCRIPTION
            "The total number of DNS replies generated by this group."
        ::= { gslbGroupStatsEntry 9 }

gslbGroupRepliesErrors OBJECT-TYPE
        SYNTAX     Counter64
        MAX-ACCESS read-only
        STATUS     current
        DESCRIPTION
            "The count of DNS error replies generated by this group."
        ::= { gslbGroupStatsEntry 10 }

gslbGroupStickyTableEntries OBJECT-TYPE
        SYNTAX     Counter64
        MAX-ACCESS read-only
        STATUS     current
        DESCRIPTION
            "The number of entries in this groups RTT sticky table."
        ::= { gslbGroupStatsEntry 11 }

gslbMemberStats OBJECT IDENTIFIER ::= { gslbStats 5 }

gslbMemberStatsTable OBJECT-TYPE
        SYNTAX     SEQUENCE OF GslbMemberStatsEntry
        MAX-ACCESS not-accessible
        STATUS     current
        DESCRIPTION
            "The (conceptual) table listing all the GSLB ResolverGroupMembers."
        ::= { gslbMemberStats 1 }

gslbMemberStatsEntry OBJECT-TYPE
        SYNTAX     GslbMemberStatsEntry
        MAX-ACCESS not-accessible
        STATUS     current
        DESCRIPTION
            "An entry (conceptual row) in the gslbMemberTable."
        INDEX      { gslbMemberResolverUUID,
					 gslbMemberGroupUUID,
					 gslbMemberUUID }
        ::= { gslbMemberStatsTable 1 }

GslbMemberStatsEntry ::=
		SEQUENCE {
			gslbMemberResolverUUID
				DisplayString,

			gslbMemberGroupUUID
				DisplayString,

			gslbMemberUUID
				DisplayString,

			gslbMemberResolverName
				DisplayString,

			gslbMemberGroupName
				DisplayString,

			gslbMemberName
				DisplayString,

			gslbMemberTopCount
				Counter64,

			gslbMemberTotalCount
				Counter64

		}

gslbMemberResolverUUID OBJECT-TYPE
        SYNTAX     DisplayString
        MAX-ACCESS read-only
        STATUS     current
        DESCRIPTION
            "The UUID of the resolver this member belongs to, used to index into the table."
        ::= { gslbMemberStatsEntry 1 }

gslbMemberGroupUUID OBJECT-TYPE
        SYNTAX     DisplayString
        MAX-ACCESS read-only
        STATUS     current
        DESCRIPTION
            "The UUID of the group this member belongs to, used to index into the table."
        ::= { gslbMemberStatsEntry 2 }

gslbMemberUUID OBJECT-TYPE
        SYNTAX     DisplayString
        MAX-ACCESS read-only
        STATUS     current
        DESCRIPTION
            "The unique UUID of a ResolverGroupMember, used to index into the table."
        ::= { gslbMemberStatsEntry 3 }

gslbMemberResolverName OBJECT-TYPE
        SYNTAX     DisplayString
        MAX-ACCESS read-only
        STATUS     current
        DESCRIPTION
            "The name of the resolver this member belongs to, provided for
display purposes."
        ::= { gslbMemberStatsEntry 4 }

gslbMemberGroupName OBJECT-TYPE
        SYNTAX     DisplayString
        MAX-ACCESS read-only
        STATUS     current
        DESCRIPTION
            "The name of the group this member belongs to, provided for
display purposes."
        ::= { gslbMemberStatsEntry 5 }

gslbMemberName OBJECT-TYPE
        SYNTAX     DisplayString
        MAX-ACCESS read-only
        STATUS     current
        DESCRIPTION
            "The name of this member."
        ::= { gslbMemberStatsEntry 6 }

gslbMemberTopCount OBJECT-TYPE
        SYNTAX     Counter64
        MAX-ACCESS read-only
        STATUS     current
        DESCRIPTION
            "The number of times this member has been served first in a DNS
            reply."
        ::= { gslbMemberStatsEntry 7 }

gslbMemberTotalCount OBJECT-TYPE
        SYNTAX     Counter64
        MAX-ACCESS read-only
        STATUS     current
        DESCRIPTION
            "The total number of times this member has been served in a DNS
            reply."
        ::= { gslbMemberStatsEntry 8 }

---------------------------------------------------------------------------
-- Failover Statistics
-- These statistics are retrieved dynamically from the failover
-- component. If the failover component is not used, then 
-- DX will not return any value for them.
---------------------------------------------------------------------------
failoverStats OBJECT IDENTIFIER ::= { dxStats 7 }

failoverStickyStats OBJECT IDENTIFIER ::= { failoverStats 1 }

failoverStickyFsRecvCount OBJECT-TYPE
        SYNTAX     INTEGER
        MAX-ACCESS read-only
        STATUS     current
        DESCRIPTION
            "The count of Full Syncs received."
        ::= { failoverStickyStats 1 }

failoverStickyFsRecvCount OBJECT-TYPE
        SYNTAX     INTEGER
        MAX-ACCESS read-only
        STATUS     current
        DESCRIPTION
            "The count of Full Syncs received."
        ::= { failoverStickyStats 1 }

failoverStickyFsSendCount OBJECT-TYPE
        SYNTAX     INTEGER
        MAX-ACCESS read-only
        STATUS     current
        DESCRIPTION
            "The count of Full Syncs sent."
        ::= { failoverStickyStats 2 }

failoverStickyDsRecvCount OBJECT-TYPE
        SYNTAX     INTEGER
        MAX-ACCESS read-only
        STATUS     current
        DESCRIPTION
            "The count of Delta Syncs received."
        ::= { failoverStickyStats 3 }

failoverStickyDsSendCount OBJECT-TYPE
        SYNTAX     INTEGER
        MAX-ACCESS read-only
        STATUS     current
        DESCRIPTION
            "The count of Delta Syncs sent."
        ::= { failoverStickyStats 4 }

failoverStickyFsReqRecvCount OBJECT-TYPE
        SYNTAX     INTEGER
        MAX-ACCESS read-only
        STATUS     current
        DESCRIPTION
            "The count of Full Sync requests received."
        ::= { failoverStickyStats 5 }

failoverStickyFsReqSendCount OBJECT-TYPE
        SYNTAX     INTEGER
        MAX-ACCESS read-only
        STATUS     current
        DESCRIPTION
            "The count of Full Sync requests sent."
        ::= { failoverStickyStats 6 }

failoverRuntimeStatus OBJECT-TYPE
        SYNTAX     INTEGER { Discover(0), Master(1), Standby(2), Idle(3) }
        MAX-ACCESS read-only
        STATUS     current
        DESCRIPTION
            "The current failover status/state of the unit. This is 
			 a run-time status and can change dynamically."
        ::= { failoverStats 2 }

END
