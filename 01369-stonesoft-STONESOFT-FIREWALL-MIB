STONESOFT-FIREWALL-MIB DEFINITIONS ::= BEGIN

      -- SUBTREE: 1.3.6.1.4.1.1369.5.2
        -- iso.org.dod.internet.private.enterprises.stonesoft.stonesoftProducts.stonesoftFirewall

IMPORTS
    Integer32, Counter32, Counter64, Unsigned32, MODULE-IDENTITY, OBJECT-TYPE, NOTIFICATION-TYPE
        FROM SNMPv2-SMI
    DisplayString, TimeStamp, TEXTUAL-CONVENTION
        FROM SNMPv2-TC
    OBJECT-GROUP, NOTIFICATION-GROUP, MODULE-COMPLIANCE
        FROM SNMPv2-CONF
    InetAddressIPv4, InetAddressIPv6
        FROM INET-ADDRESS-MIB
    stonesoftModules, stonesoftFirewall
        FROM STONESOFT-SMI-MIB;

stonesoftFirewallMibModule MODULE-IDENTITY
      LAST-UPDATED      "201202010000Z"
      ORGANIZATION      "Stonesoft Corporation"
      CONTACT-INFO      "email: support@stonesoft.com"
      DESCRIPTION       "MIB for Stonesoft's Firewall products"
      REVISION          "201202010000Z"
      DESCRIPTION       "Forwarded packets statistics added"
      REVISION	        "201110310000Z"
      DESCRIPTION       "VPN end-point statistics added"
      REVISION	        "201106010000Z"
      DESCRIPTION       "Firewall related statistics objects introduced"
      REVISION	        "200406160000Z"
      DESCRIPTION       "First public revision"
      ::= { stonesoftModules 3 }


firewallObjects     OBJECT IDENTIFIER ::= { stonesoftFirewall 1 }
firewallEvents      OBJECT IDENTIFIER ::= { stonesoftFirewall 2 }
firewallEventsV2    OBJECT IDENTIFIER ::= { firewallEvents 0 }
firewallConformance OBJECT IDENTIFIER ::= { stonesoftFirewall 3 }

--
-- Firewall objects
--
fwSoftwareVersion   OBJECT-TYPE
              SYNTAX        DisplayString
              MAX-ACCESS    read-only
              STATUS        current
              DESCRIPTION
                  "Version string of the firewall software"
              ::= { firewallObjects 1 }

fwSecurityPolicy  OBJECT-TYPE
              SYNTAX        DisplayString
              MAX-ACCESS    read-only
              STATUS        current
              DESCRIPTION
                  "Name of the current security policy on the
                  firewall"
              ::= { firewallObjects 2 }

fwPolicyTime  OBJECT-TYPE
              SYNTAX        TimeStamp
              MAX-ACCESS    read-only
              STATUS        current
              DESCRIPTION
                  "The time when the security policy was
                  installed to the firewall"
              ::= { firewallObjects 3 }

-- Global firewall informations

fwConnNumber OBJECT-TYPE
              SYNTAX        Counter64
              MAX-ACCESS    read-only
              STATUS        current
              DESCRIPTION
                  "Number of current connections"
              ::= { firewallObjects 4 }

fwAccepted OBJECT-TYPE
              SYNTAX        Counter64
              MAX-ACCESS    read-only
              STATUS        current
              DESCRIPTION
                  "Number of accepted packets"
              ::= { firewallObjects 5 }

fwDropped OBJECT-TYPE
              SYNTAX        Counter64
              MAX-ACCESS    read-only
              STATUS        current
              DESCRIPTION
                  "Number of dropped packets"
              ::= { firewallObjects 6 }

fwLogged OBJECT-TYPE
              SYNTAX        Counter64
              MAX-ACCESS    read-only
              STATUS        current
              DESCRIPTION
                  "Number of logged packets"
              ::= { firewallObjects 7 }

fwAccounted OBJECT-TYPE
              SYNTAX        Counter64
              MAX-ACCESS    read-only
              STATUS        current
              DESCRIPTION
                  "Number of accounted packets"
              ::= { firewallObjects 8 }

fwRejected OBJECT-TYPE
              SYNTAX        Counter64
              MAX-ACCESS    read-only
              STATUS        current
              DESCRIPTION
                  "Number of rejected packets"
              ::= { firewallObjects 9 }


-- interface related objects

fwIfStatsTable  OBJECT-TYPE
              SYNTAX        SEQUENCE OF FwIfStatsEntry
              MAX-ACCESS    not-accessible
              STATUS        current
              DESCRIPTION
                  "This table contains an entry for each
                   interface in system"
              ::= { firewallObjects 10 }

-- Statistics

fwIfStatsEntry OBJECT-TYPE
              SYNTAX        FwIfStatsEntry
              MAX-ACCESS    not-accessible
              STATUS        current
              DESCRIPTION   "Row for a interface"
              INDEX         { fwIfStatsIndex }
              ::= { fwIfStatsTable 1 }

FwIfStatsEntry ::=
    SEQUENCE {
            fwIfStatsIndex        INTEGER,
            fwIfName              DisplayString,
            fwIfAcceptedPkts      Counter64,
            fwIfDroppedPkts       Counter64,
            fwIfLoggedPkts        Counter64,
            fwIfAccountedPkts     Counter64,
            fwIfRejectedPkts      Counter64,
            fwIfAcceptedBytes     Counter64,
            fwIfDroppedBytes      Counter64,
            fwIfLoggedBytes       Counter64,
            fwIfAccountedBytes    Counter64,
            fwIfRejectedBytes     Counter64,
            fwIfForwardedPkts     Counter64,
            fwIfForwardedBytes    Counter64
            }

fwIfStatsIndex OBJECT-TYPE
              SYNTAX        Integer32(1..2147483647)
              MAX-ACCESS    not-accessible
              STATUS        current
              DESCRIPTION
                "A unique value, greater than zero, for each interface or
                 interface sub-layer in the managed system."
              ::= { fwIfStatsEntry 1 }

fwIfName	OBJECT-TYPE
              SYNTAX        DisplayString
              MAX-ACCESS    read-only
              STATUS        current
              DESCRIPTION
                  "Name of interface"
              ::= { fwIfStatsEntry 2 }

fwIfAcceptedPkts OBJECT-TYPE
              SYNTAX        Counter64
              MAX-ACCESS    read-only
              STATUS        current
              DESCRIPTION
                  "Number of accepted packets by firewall rules"
              ::= { fwIfStatsEntry 3 }

fwIfDroppedPkts OBJECT-TYPE
              SYNTAX        Counter64
              MAX-ACCESS    read-only
              STATUS        current
              DESCRIPTION
                  "Number of dropped packets by firewall rules"
              ::= { fwIfStatsEntry 4 }

fwIfLoggedPkts OBJECT-TYPE
              SYNTAX        Counter64
              MAX-ACCESS    read-only
              STATUS        current
              DESCRIPTION
                  "Number of logged packets by firewall rules"
              ::= { fwIfStatsEntry 5 }

fwIfAccountedPkts OBJECT-TYPE
              SYNTAX        Counter64
              MAX-ACCESS    read-only
              STATUS        current
              DESCRIPTION
                  "Number of logged packets by firewall rules"
              ::= { fwIfStatsEntry 6 }

fwIfRejectedPkts OBJECT-TYPE
              SYNTAX        Counter64
              MAX-ACCESS    read-only
              STATUS        current
              DESCRIPTION
                  "Number of rejected packets by firewall rules"
              ::= { fwIfStatsEntry 7 }

fwIfAcceptedBytes	OBJECT-TYPE
              SYNTAX        Counter64
              MAX-ACCESS    read-only
              STATUS        current
              DESCRIPTION
                  "Number of accepted bytes by firewall rules"
              ::= { fwIfStatsEntry 8 }

fwIfDroppedBytes	OBJECT-TYPE
              SYNTAX        Counter64
              MAX-ACCESS    read-only
              STATUS        current
              DESCRIPTION
                  "Number of dropped bytes by firewall rules"
              ::= { fwIfStatsEntry 9 }

fwIfLoggedBytes	OBJECT-TYPE
              SYNTAX        Counter64
              MAX-ACCESS    read-only
              STATUS        current
              DESCRIPTION
                  "Number of logged bytes by firewall rules"
              ::= { fwIfStatsEntry 10 }

fwIfAccountedBytes	OBJECT-TYPE
              SYNTAX        Counter64
              MAX-ACCESS    read-only
              STATUS        current
              DESCRIPTION
                  "Number of accounted bytes by firewall rules"
              ::= { fwIfStatsEntry 11 }

fwIfRejectedBytes	OBJECT-TYPE
              SYNTAX        Counter64
              MAX-ACCESS    read-only
              STATUS        current
              DESCRIPTION
                  "Number of rejected bytes by firewall rules"
              ::= { fwIfStatsEntry 12 }

fwIfForwardedPkts OBJECT-TYPE
              SYNTAX        Counter64
              MAX-ACCESS    read-only
              STATUS        current
              DESCRIPTION
                  "Number of forwarded packets by firewall rules"
              ::= { fwIfStatsEntry 13 }

fwIfForwardedBytes OBJECT-TYPE
              SYNTAX        Counter64
              MAX-ACCESS    read-only
              STATUS        current
              DESCRIPTION
                  "Number of forwarded bytes by firewall rules"
              ::= { fwIfStatsEntry 14 }

-- hardware related objects

fwHardware OBJECT IDENTIFIER ::= { firewallObjects 11 }


-- Processor

fwCpuStatsTable  OBJECT-TYPE
              SYNTAX        SEQUENCE OF FwCpuEntry
              MAX-ACCESS    not-accessible
              STATUS        current
              DESCRIPTION   "This table contains an entry for each cpu in
                            a system and total usage of all cpus."
              ::= { fwHardware 1 }

fwCpuStatsEntry OBJECT-TYPE
              SYNTAX        FwCpuEntry
              MAX-ACCESS    not-accessible
              STATUS        current
              DESCRIPTION   "Row with information about cpu usage"
              INDEX         { fwCpuStatsId }
              ::= { fwCpuStatsTable 1 }

FwCpuEntry ::= SEQUENCE {
            fwCpuStatsId    INTEGER,
            fwCpuName       DisplayString,
            fwCpuTotal      Unsigned32,
            fwCpuUser       Unsigned32,
            fwCpuSystem     Unsigned32,
            fwCpuNice       Unsigned32,
            fwCpuIdle       Unsigned32,
            fwCpuIoWait     Unsigned32,
            fwCpuHwIrq      Unsigned32,
            fwCpuSoftIrq    Unsigned32
            }


fwCpuStatsId     OBJECT-TYPE
              SYNTAX        Integer32(1..1024)
              MAX-ACCESS    not-accessible
              STATUS        current
              DESCRIPTION   "A unique value, greater than zero, for each
                             CPU in the managed system. First element with Id '0'
                             is designed for total values."
              ::= { fwCpuStatsEntry 1 }

fwCpuName   OBJECT-TYPE
              SYNTAX        DisplayString (SIZE (0..255))
              MAX-ACCESS    read-only
              STATUS        current
              DESCRIPTION   "Name of data current line concern"
              ::= { fwCpuStatsEntry 2 }

fwCpuTotal  OBJECT-TYPE
              SYNTAX        Unsigned32
              UNITS         "percent"
              MAX-ACCESS    read-only
              STATUS        current
              DESCRIPTION   "The total CPU load percentage"
              ::= { fwCpuStatsEntry 3 }

fwCpuUser   OBJECT-TYPE
              SYNTAX        Unsigned32
              UNITS         "percent"
              MAX-ACCESS    read-only
              STATUS        current
              DESCRIPTION   "The percentage of time the CPU has spent running
                             users' processes that are not niced"
              ::= { fwCpuStatsEntry 4 }

fwCpuSystem OBJECT-TYPE
              SYNTAX        Unsigned32
              UNITS         "percent"
              MAX-ACCESS    read-only
              STATUS        current
              DESCRIPTION   "The percentage of time the CPU has spent running
                             the kernel and its processes"
              ::= { fwCpuStatsEntry 5 }

fwCpuNice   OBJECT-TYPE
              SYNTAX        Unsigned32
              UNITS         "percent"
              MAX-ACCESS    read-only
              STATUS        current
              DESCRIPTION   "The percentage of time the CPU has spent running
                             users' proccess that have been niced"
              ::= { fwCpuStatsEntry 6 }

fwCpuIdle   OBJECT-TYPE
              SYNTAX        Unsigned32
              UNITS         "percent"
              MAX-ACCESS    read-only
              STATUS        current
              DESCRIPTION   "The percentage of time the CPU was idle"
              ::= { fwCpuStatsEntry 7 }

fwCpuIoWait OBJECT-TYPE
              SYNTAX        Unsigned32
              UNITS         "percent"
              MAX-ACCESS    read-only
              STATUS        current
              DESCRIPTION   "The percentage of time the CPU has been waiting
                             for I/O to complete"
              ::= { fwCpuStatsEntry 8 }

fwCpuHwIrq  OBJECT-TYPE
              SYNTAX        Unsigned32
              UNITS         "percent"
              MAX-ACCESS    read-only
              STATUS        current
              DESCRIPTION   "The percentage of time the CPU has been servicing
                             hardware interrupts"
              ::= { fwCpuStatsEntry 9 }

fwCpuSoftIrq OBJECT-TYPE
              SYNTAX        Unsigned32
              UNITS         "percent"
              MAX-ACCESS    read-only
              STATUS        current
              DESCRIPTION   "The percentage of time the CPU has been servicing
                             software interrupts"
              ::= { fwCpuStatsEntry 10 }


-- Memory

fwMemoryInfo OBJECT IDENTIFIER ::= { fwHardware 2 }


fwSwapBytesTotal OBJECT-TYPE
              SYNTAX      Counter64
              UNITS       "bytes"
              MAX-ACCESS  read-only
              STATUS      current
              DESCRIPTION "Total swap space"
              ::= { fwMemoryInfo 1 }

fwSwapBytesUsed OBJECT-TYPE
              SYNTAX      Counter64
              UNITS       "bytes"
              MAX-ACCESS  read-only
              STATUS      current
              DESCRIPTION "Used space of swap"
              ::= { fwMemoryInfo 2 }

fwSwapBytesUnused OBJECT-TYPE
              SYNTAX      Counter64
              UNITS       "bytes"
              MAX-ACCESS  read-only
              STATUS      current
              DESCRIPTION "Amount of unused space of swap"
              ::= { fwMemoryInfo 3 }


fwMemBytesTotal OBJECT-TYPE
              SYNTAX      Counter64
              UNITS       "bytes"
              MAX-ACCESS  read-only
              STATUS      current
              DESCRIPTION "Number of available bytes of physical memory"
              ::= { fwMemoryInfo 4 }

fwMemBytesUsed OBJECT-TYPE
              SYNTAX      Counter64
              UNITS       "bytes"
              MAX-ACCESS  read-only
              STATUS      current
              DESCRIPTION "Amount of memory being in use"
              ::= { fwMemoryInfo 5 }

fwMemBytesUnused OBJECT-TYPE
              SYNTAX      Counter64
              UNITS       "bytes"
              MAX-ACCESS  read-only
              STATUS      current
              DESCRIPTION "Amount of unused bytes of physical memory"
              ::= { fwMemoryInfo 6 }

fwMemBytesBuffers OBJECT-TYPE
              SYNTAX      Counter64
              UNITS       "bytes"
              MAX-ACCESS  read-only
              STATUS      current
              DESCRIPTION "Amount of memory used as buffers"
              ::= { fwMemoryInfo 7 }

fwMemBytesCached OBJECT-TYPE
              SYNTAX      Counter64
              UNITS       "bytes"
              MAX-ACCESS  read-only
              STATUS      current
              DESCRIPTION "Amount of memory used as cache"
              ::= { fwMemoryInfo 8 }



-- disk(s) statistics

fwDiskStatsTable  OBJECT-TYPE
              SYNTAX        SEQUENCE OF FwDiskStatsEntry
              MAX-ACCESS    not-accessible
              STATUS        current
              DESCRIPTION   "Table contains an entry for each partition
                             mounted in a system."
              ::= { fwHardware 3 }

fwDiskStatsEntry OBJECT-TYPE
              SYNTAX        FwDiskStatsEntry
              MAX-ACCESS    not-accessible
              STATUS        current
              DESCRIPTION   "Row of information concerning one partition"
              INDEX         { fwPartitionIndex }
              ::= { fwDiskStatsTable 1 }

FwDiskStatsEntry ::= SEQUENCE {
                fwPartitionIndex    INTEGER,
                fwPartitionDevName  DisplayString,
                fwMountPointName    DisplayString,
                fwPartitionSize     Counter64,
                fwPartitionUsed     Counter64,
                fwPartitionAvail    Counter64
            }


fwPartitionIndex  OBJECT-TYPE
              SYNTAX        Integer32(1..1024)
              MAX-ACCESS    not-accessible
              STATUS        current
              DESCRIPTION   "A unique value, greater than zero, for each partition"
              ::= { fwDiskStatsEntry 1 }

fwPartitionDevName  OBJECT-TYPE
              SYNTAX        DisplayString (SIZE (0..255))
              MAX-ACCESS    read-only
              STATUS        current
              DESCRIPTION   "A unique name of a device"
              ::= { fwDiskStatsEntry 2 }

fwMountPointName    OBJECT-TYPE
              SYNTAX        DisplayString (SIZE (0..255))
              MAX-ACCESS    read-only
              STATUS        current
              DESCRIPTION   "Name of a mount point"
              ::= { fwDiskStatsEntry 3 }

fwPartitionSize OBJECT-TYPE
              SYNTAX        Counter64
              UNITS         "kbytes"
              MAX-ACCESS    read-only
              STATUS        current
              DESCRIPTION   "Total size of the partition"
              ::= { fwDiskStatsEntry 4 }

fwPartitionUsed OBJECT-TYPE
              SYNTAX        Counter64
              UNITS         "kbytes"
              MAX-ACCESS    read-only
              STATUS        current
              DESCRIPTION   "Amount of used space of the partition
                             (in kilobytes)"
              ::= { fwDiskStatsEntry 5 }

fwPartitionAvail    OBJECT-TYPE
              SYNTAX        Counter64
              UNITS         "kbytes"
              MAX-ACCESS    read-only
              STATUS        current
              DESCRIPTION   "Information about amount of free space on
                             partition (in kilobytes)"
              ::= { fwDiskStatsEntry 6 }

-- ADSL related objects

fwADSL        OBJECT IDENTIFIER ::= { firewallObjects 12 }

adslModulation OBJECT-TYPE
              SYNTAX        DisplayString
              MAX-ACCESS    read-only
              STATUS        current
              DESCRIPTION
                  "Modulation protocol"
              ::= { fwADSL 1 }

adslChannel OBJECT-TYPE
              SYNTAX        DisplayString
              MAX-ACCESS    read-only
              STATUS        current
              DESCRIPTION   "Channel type"
              ::= { fwADSL 2 }

adslConnStatus OBJECT-TYPE
              SYNTAX        DisplayString
              MAX-ACCESS    read-only
              STATUS        current
              DESCRIPTION   "The status of the DSL link or communication status
                             with DSL modem in case of communication error."
              ::= { fwADSL 3 }

adslConnUptime OBJECT-TYPE
              SYNTAX        TimeStamp
              MAX-ACCESS    read-only
              STATUS        current
              DESCRIPTION   "Uptime of current ADSL connection."
              ::= { fwADSL 4 }

adslLineStatus OBJECT-TYPE
              SYNTAX        DisplayString
              MAX-ACCESS    read-only
              STATUS        current
              DESCRIPTION   "Current status of DSL line."
              ::= { fwADSL 5 }

adslInOctets OBJECT-TYPE
              SYNTAX        Integer32
              MAX-ACCESS    read-only
              STATUS        current
              DESCRIPTION   "Number of bytes received by ADSL interface"
              ::= { fwADSL 6 }

adslOutOctets OBJECT-TYPE
              SYNTAX        Integer32
              MAX-ACCESS    read-only
              STATUS        current
              DESCRIPTION   "Number of bytes transmitted by ADSL interface"
              ::= { fwADSL 7 }

adslSynchroSpeedUp OBJECT-TYPE
              SYNTAX        Integer32
              MAX-ACCESS    read-only
              STATUS        current
              DESCRIPTION   "The actual rate at which data is flowing upstream."
              ::= { fwADSL 8 }

adslSynchroSpeedDown OBJECT-TYPE
              SYNTAX        Integer32
              MAX-ACCESS    read-only
              STATUS        current
              DESCRIPTION   "The actual rate at which data is flowing downstream."
              ::= { fwADSL 9 }

adslAttenuationUp OBJECT-TYPE
              SYNTAX        Integer32
              MAX-ACCESS    read-only
              STATUS        current
              DESCRIPTION   "An estimate of the average loop attenuation upstream."
              ::= { fwADSL 10 }

adslAttenuationDown OBJECT-TYPE
              SYNTAX        Integer32
              MAX-ACCESS    read-only
              STATUS        current
              DESCRIPTION   "An estimate of the average loop attenuation downstream."
              ::= { fwADSL 11 }

adslNoiseMarginUp OBJECT-TYPE
              SYNTAX        Integer32
              MAX-ACCESS    read-only
              STATUS        current
              DESCRIPTION   "This is a signal-to-noise ratio (SNR) margin for
                             traffic going upstream"
              ::= { fwADSL 12 }

adslNoiseMarginDown OBJECT-TYPE
              SYNTAX        Integer32
              MAX-ACCESS    read-only
              STATUS        current
              DESCRIPTION   "This is a signal-to-noise ratio (SNR) margin for
                             traffic going downstream"
              ::= { fwADSL 13 }

adslHecErrorsUp OBJECT-TYPE
              SYNTAX        Integer32
              MAX-ACCESS    read-only
              STATUS        current
              DESCRIPTION   "The total number of header error checksum errors upstream."
              ::= { fwADSL 14 }

adslHecErrorsDown OBJECT-TYPE
              SYNTAX        Integer32
              MAX-ACCESS    read-only
              STATUS        current
              DESCRIPTION   "The total number of header error checksum errors downstream."
              ::= { fwADSL 15 }

adslOcdErrorsUp OBJECT-TYPE
              SYNTAX        Integer32
              MAX-ACCESS    read-only
              STATUS        current
              DESCRIPTION   "The number of out-of-cell delineation errors upstream."
              ::= { fwADSL 16 }

adslOcdErrorsDown OBJECT-TYPE
              SYNTAX        Integer32
              MAX-ACCESS    read-only
              STATUS        current
              DESCRIPTION   "The number of out-of-cell delineation errors downstream."
              ::= { fwADSL 17 }

adslLcdErrorsUp OBJECT-TYPE
              SYNTAX        Integer32
              MAX-ACCESS    read-only
              STATUS        current
              DESCRIPTION   "The total of lost-cell-delineation errors upstream."
              ::= { fwADSL 18 }

adslLcdErrorsDown OBJECT-TYPE
              SYNTAX        Integer32
              MAX-ACCESS    read-only
              STATUS        current
              DESCRIPTION   "The total of lost-cell-delineation errors downstream."
              ::= { fwADSL 19 }

adslBitErrorsUp OBJECT-TYPE
              SYNTAX        Integer32
              MAX-ACCESS    read-only
              STATUS        current
              DESCRIPTION   "The number of bit errors upstream."
              ::= { fwADSL 20 }

adslBitErrorsDown OBJECT-TYPE
              SYNTAX        Integer32
              MAX-ACCESS    read-only
              STATUS        current
              DESCRIPTION   "The number of bit errors downstream."
              ::= { fwADSL 21 }

-- VPN end-point related objects

VpnEndpointType ::= TEXTUAL-CONVENTION
    STATUS      current
    DESCRIPTION
        "A value that represents the type of the remote VPN end-point.

         unknown(0)  The type of the remote VPN end-point is not known.

         static(1)   The remote VPN end-point has a static IP address.

         dynamic(2)  The remote VPN end-point has a dynamic IP address.

         mobile(3)   The remote is a mobile VPN client."
    SYNTAX       INTEGER {
                     unknown(0),
                     static(1),
                     dynamic(2),
                     mobile(3)
                 }

-- IPv4 end-points --

fwVpnEp4Table OBJECT-TYPE
              SYNTAX        SEQUENCE OF FwVpnEp4Entry
              MAX-ACCESS    not-accessible
              STATUS        current
              DESCRIPTION   "This table contains an entry for each
                             IPv4 VPN end-point pair"
              ::= { firewallObjects 13 }

fwVpnEp4Entry OBJECT-TYPE
              SYNTAX        FwVpnEp4Entry
              MAX-ACCESS    not-accessible
              STATUS        current
              DESCRIPTION   "Row for an IPv4 VPN end-point pair"
              INDEX         { fwVpnEp4Index }
              ::= { fwVpnEp4Table 1 }

FwVpnEp4Entry ::=
    SEQUENCE {
            fwVpnEp4Index             INTEGER,
            fwVpnEp4Local             InetAddressIPv4,
            fwVpnEp4Remote            InetAddressIPv4,
            fwVpnEp4RemoteType        VpnEndpointType,
            fwVpnEp4ReceivedBytes     Counter64,
            fwVpnEp4SentBytes         Counter64,
            fwVpnEp4IpsecSa           Counter32
            }

fwVpnEp4Index OBJECT-TYPE
              SYNTAX        Integer32(1..2147483647)
              MAX-ACCESS    not-accessible
              STATUS        current
              DESCRIPTION   "A unique value, greater than zero, for each
                             end-point pair."
              ::= { fwVpnEp4Entry 1 }

fwVpnEp4Local OBJECT-TYPE
              SYNTAX        InetAddressIPv4
              MAX-ACCESS    read-only
              STATUS        current
              DESCRIPTION   "Local IPv4 end-point address"
              ::= { fwVpnEp4Entry 2 }

fwVpnEp4Remote OBJECT-TYPE
              SYNTAX        InetAddressIPv4
              MAX-ACCESS    read-only
              STATUS        current
              DESCRIPTION   "Remote IPv4 end-point address"
              ::= { fwVpnEp4Entry 3 }

fwVpnEp4RemoteType OBJECT-TYPE
              SYNTAX        VpnEndpointType
              MAX-ACCESS    read-only
              STATUS        current
              DESCRIPTION   "The type of remote VPN end-point"
              ::= { fwVpnEp4Entry 4 }

fwVpnEp4ReceivedBytes OBJECT-TYPE
              SYNTAX        Counter64
              MAX-ACCESS    read-only
              STATUS        current
              DESCRIPTION   "Number of received bytes between the end-point pair"
              ::= { fwVpnEp4Entry 5 }

fwVpnEp4SentBytes OBJECT-TYPE
              SYNTAX        Counter64
              MAX-ACCESS    read-only
              STATUS        current
              DESCRIPTION   "Number of sent bytes between the end-point pair"
              ::= { fwVpnEp4Entry 6 }

fwVpnEp4IpsecSa OBJECT-TYPE
              SYNTAX        Counter32
              MAX-ACCESS    read-only
              STATUS        current
              DESCRIPTION   "Number of currently established IPsec SAs
                   between the end-point pair"
              ::= { fwVpnEp4Entry 7 }

-- IPv6 end-points --

fwVpnEp6Table OBJECT-TYPE
              SYNTAX        SEQUENCE OF FwVpnEp6Entry
              MAX-ACCESS    not-accessible
              STATUS        current
              DESCRIPTION   "This table contains an entry for each
                             IPv6 VPN end-point pair"
              ::= { firewallObjects 14 }

fwVpnEp6Entry OBJECT-TYPE
              SYNTAX        FwVpnEp6Entry
              MAX-ACCESS    not-accessible
              STATUS        current
              DESCRIPTION   "Row for an IPv6 VPN end-point pair"
              INDEX         { fwVpnEp6Index }
              ::= { fwVpnEp6Table 1 }

FwVpnEp6Entry ::=
    SEQUENCE {
            fwVpnEp6Index             INTEGER,
            fwVpnEp6Local             InetAddressIPv6,
            fwVpnEp6Remote            InetAddressIPv6,
            fwVpnEp6RemoteType        VpnEndpointType,
            fwVpnEp6ReceivedBytes     Counter64,
            fwVpnEp6SentBytes         Counter64,
            fwVpnEp6IpsecSa           Counter32
            }

fwVpnEp6Index OBJECT-TYPE
              SYNTAX        Integer32(1..2147483647)
              MAX-ACCESS    not-accessible
              STATUS        current
              DESCRIPTION   "A unique value, greater than zero, for each
                             end-point pair."
              ::= { fwVpnEp6Entry 1 }

fwVpnEp6Local OBJECT-TYPE
              SYNTAX        InetAddressIPv6
              MAX-ACCESS    read-only
              STATUS        current
              DESCRIPTION   "Local IPv6 end-point address"
              ::= { fwVpnEp6Entry 2 }

fwVpnEp6Remote OBJECT-TYPE
              SYNTAX        InetAddressIPv6
              MAX-ACCESS    read-only
              STATUS        current
              DESCRIPTION   "Remote IPv6 end-point address"
              ::= { fwVpnEp6Entry 3 }

fwVpnEp6RemoteType OBJECT-TYPE
              SYNTAX        VpnEndpointType
              MAX-ACCESS    read-only
              STATUS        current
              DESCRIPTION   "The type of remote VPN end-point"
              ::= { fwVpnEp6Entry 4 }

fwVpnEp6ReceivedBytes OBJECT-TYPE
              SYNTAX        Counter64
              MAX-ACCESS    read-only
              STATUS        current
              DESCRIPTION   "Number of received bytes between the end-point pair"
              ::= { fwVpnEp6Entry 5 }

fwVpnEp6SentBytes OBJECT-TYPE
              SYNTAX        Counter64
              MAX-ACCESS    read-only
              STATUS        current
              DESCRIPTION   "Number of sent bytes between the end-point pair"
              ::= { fwVpnEp6Entry 6 }

fwVpnEp6IpsecSa OBJECT-TYPE
              SYNTAX        Counter32
              MAX-ACCESS    read-only
              STATUS        current
              DESCRIPTION   "Number of currently established IPsec SAs
                   between the end-point pair"
              ::= { fwVpnEp6Entry 7 }

--
-- Firewall events
--

fwPolicyInstall     NOTIFICATION-TYPE
              OBJECTS       { fwSecurityPolicy }
              STATUS        current
              DESCRIPTION   "A firewall policy was (re)installed"
              ::= {firewallEventsV2 1 }

-- Conformance information

firewallGroups        OBJECT IDENTIFIER ::= { firewallConformance 1 }
firewallCompliances   OBJECT IDENTIFIER ::= { firewallConformance 2 }

firewallCompliance1 MODULE-COMPLIANCE
      STATUS current
      DESCRIPTION
          "The compliance statement for firewalls"
      MODULE  -- this module --
          MANDATORY-GROUPS { firewallGeneralInformationGroup,
                             firewallGeneralNotifGroup,
                             firewallGeneralStatsGroup,
                             firewallIfaceStatsGroup,
                             firewallHardwareGroup,
                             firewallAdslGroup,
                             firewallVpnEpGroup }
      ::= { firewallCompliances 1 }


firewallGeneralInformationGroup   OBJECT-GROUP
      OBJECTS	{ fwSoftwareVersion, fwSecurityPolicy, fwPolicyTime }
      STATUS	current
      DESCRIPTION
          "A collection of objects giving general information about the
           firewall"
      ::= { firewallGroups 1 }

firewallGeneralNotifGroup NOTIFICATION-GROUP
      NOTIFICATIONS	{ fwPolicyInstall }
      STATUS	current
      DESCRIPTION
          "A collection of notification giving information about
           general events in the firewall"
      ::= { firewallGroups 2 }

firewallIfaceStatsGroup  OBJECT-GROUP
      OBJECTS { fwIfName,
                fwIfAcceptedPkts, fwIfDroppedPkts, fwIfLoggedPkts,
                fwIfAccountedPkts, fwIfRejectedPkts, fwIfForwardedPkts,
                fwIfAcceptedBytes, fwIfDroppedBytes, fwIfLoggedBytes,
                fwIfAccountedBytes, fwIfRejectedBytes, fwIfForwardedBytes }
      STATUS current
      DESCRIPTION
          "A collection of objects giving information about the
           current firewall interface related traffic statistics"
      ::= { firewallGroups 3 }

firewallGeneralStatsGroup   OBJECT-GROUP
      OBJECTS	{ fwConnNumber, fwAccepted, fwDropped,
                  fwLogged, fwAccounted, fwRejected }
      STATUS	current
      DESCRIPTION
          "A collection of objects giving general information about the
           firewall traffic statistics"
      ::= { firewallGroups 4 }

firewallHardwareGroup   OBJECT-GROUP
      OBJECTS   { fwCpuName, fwCpuTotal, fwCpuUser, fwCpuSystem,
                  fwCpuNice, fwCpuIdle, fwCpuIoWait, fwCpuHwIrq, fwCpuSoftIrq,
                  fwSwapBytesTotal, fwSwapBytesUsed, fwSwapBytesUnused,
                  fwMemBytesTotal, fwMemBytesUsed, fwMemBytesUnused,
                  fwMemBytesBuffers, fwMemBytesCached,
                  fwPartitionDevName, fwMountPointName,
                  fwPartitionSize, fwPartitionUsed, fwPartitionAvail }
      STATUS    current
      DESCRIPTION
          "A collection of objects giving information about the
           hardware parameters"
      ::= { firewallGroups 5 }

firewallAdslGroup   OBJECT-GROUP
      OBJECTS	{ adslModulation, adslChannel, adslConnStatus, adslConnUptime,
                  adslLineStatus, adslInOctets, adslOutOctets,
                  adslSynchroSpeedUp, adslSynchroSpeedDown,
                  adslAttenuationUp, adslAttenuationDown, adslNoiseMarginUp,
                  adslNoiseMarginDown, adslHecErrorsUp, adslHecErrorsDown,
                  adslOcdErrorsUp, adslOcdErrorsDown, adslLcdErrorsUp,
                  adslLcdErrorsDown, adslBitErrorsUp, adslBitErrorsDown  }
      STATUS	current
      DESCRIPTION
          "A collection of objects giving information about the
           ADSL modem parameters"
      ::= { firewallGroups 6 }

firewallVpnEpGroup OBJECT-GROUP
      OBJECTS { fwVpnEp4Local, fwVpnEp4Remote, fwVpnEp4RemoteType,
                fwVpnEp4ReceivedBytes, fwVpnEp4SentBytes,
                fwVpnEp4IpsecSa, fwVpnEp6Local, fwVpnEp6Remote,
                fwVpnEp6RemoteType, fwVpnEp6ReceivedBytes,
                fwVpnEp6SentBytes, fwVpnEp6IpsecSa }
      STATUS current
      DESCRIPTION
          "A collection of objects giving information about the
           configured VPN end-point pairs"
      ::= { firewallGroups 7 }

END
