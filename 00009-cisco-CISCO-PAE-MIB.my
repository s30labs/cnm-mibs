CISCO-PAE-MIB DEFINITIONS ::= BEGIN

IMPORTS 
    OBJECT-TYPE,
    MODULE-IDENTITY 
        FROM SNMPv2-SMI

    TruthValue 
        FROM SNMPv2-TC

    MODULE-COMPLIANCE,
    OBJECT-GROUP
        FROM SNMPv2-CONF

    dot1xPaePortEntry
        FROM IEEE8021-PAE-MIB

    VlanIndex 
        FROM CISCO-VTP-MIB

    ciscoMgmt
        FROM CISCO-SMI;
    
ciscoPaeMIB MODULE-IDENTITY
    LAST-UPDATED "200210160000Z" 
    ORGANIZATION "Cisco System, Inc."
    CONTACT-INFO 
            "         Cisco Systems
                      Customer Service

              Postal: 170 W Tasman Drive
                      San Jose, CA  95134
                      USA

                 Tel: +1 800 553-NETS

        E-mail: cs-wbu@cisco.com"
    DESCRIPTION 
        "Cisco Port Access Entity (PAE) module for managing 
        IEEE Std 802.1x.

        This MIB provides Port Access Entity information that are 
        either excluded by IEEE Std 802.1x (IEEE8021-PAE-MIB) or
        specific to Cisco products."

    REVISION    "200210160000Z"
    DESCRIPTION
        "Add SNMP support for the Multiple Authentication and
         and Guest Vlan features.
         
         The objects cpaeMultipleHost has been deprecated, and 
         cpaePortMode has been added to cpaePortTable to support
         for Multiple Authentication feature. The object 
         cpaeGuestVlanId has been added to support for Guest Vlan
         feature."


    REVISION    "200105241016Z"
    DESCRIPTION
        "Initial version of this MIB module."

    ::= {ciscoMgmt 220}

cpaeMIBNotification OBJECT IDENTIFIER ::= {ciscoPaeMIB 0}
cpaeMIBObject OBJECT IDENTIFIER ::= {ciscoPaeMIB 1}

cpaePortTable OBJECT-TYPE
    SYNTAX        SEQUENCE OF CpaePortEntry
    MAX-ACCESS    not-accessible
    STATUS        current
    DESCRIPTION
        "A table of system level information for each port
        supported by the Port Access Entity.  An entry 
        appears in this table for each PAE port of this system.
        This table contains additional objects for the
        dot1xPaePortTable."
    REFERENCE
        "IEEE 802.1x Subclause 9.6.1"
    ::= {cpaeMIBObject 1}

cpaePortEntry OBJECT-TYPE
    SYNTAX        CpaePortEntry
    MAX-ACCESS    not-accessible
    STATUS        current
    DESCRIPTION    
        "An entry containing additional management information
        applicable to a particular PAE port."
    AUGMENTS    {dot1xPaePortEntry}
    ::= {cpaePortTable 1}


CpaePortEntry ::= SEQUENCE {
    cpaeMultipleHost    TruthValue,
    cpaePortMode        INTEGER
}

cpaeMultipleHost OBJECT-TYPE
    SYNTAX        TruthValue
    MAX-ACCESS    read-write
    STATUS        deprecated
    DESCRIPTION
        "Specifies whether the port allows multiple-host connection
        or not."
    ::= {cpaePortEntry 1}

cpaePortMode OBJECT-TYPE
    SYNTAX        INTEGER {
                     singleHost(1),
                     multiHost(2),
                     multiAuth(3)
                  }
    MAX-ACCESS    read-write
    STATUS        current
    DESCRIPTION
        "Specifies the current mode of dot1x operation on the port.
            - singleHost(1): port allows one host to connect and
                 authenticate.
            - multiHost(2) : port allows multiple hosts to connect.
                 Once a host is authenticated, all remaining hosts
                 are also authorized.
            - multiAuth(3) : port allows multiple hosts to connect.
                 Authorized hosts will be secured by Port Security
                 feature. The number of hosts that can be authorized
                 is restricted by the maximum hosts allowed by Port
                 Security, which is controlled by the object
                 portSecurityMaxSrcAddr in portSecurityTable."
    REFERENCE
        "CISCO-STACK-MIB, portSecurityTable"
    ::= {cpaePortEntry 2}


cpaeGuestVlanId OBJECT-TYPE
    SYNTAX       VlanIndex
    MAX-ACCESS   read-write
    STATUS       current
    DESCRIPTION
        "Specifies the Guest Vlan of the system. An interface in
         singleHost(1) mode will be moved to Guest Vlan if its 
         access is unsuccessfully authenticated. A value of zero
         indicates no Guest Vlan configured in the system."
    ::= {cpaeMIBObject 2}

------------------------------------------
-- Conformance Information
------------------------------------------
cpaeMIBConformance OBJECT IDENTIFIER ::= {ciscoPaeMIB 2}
cpaeMIBCompliances OBJECT IDENTIFIER ::= {cpaeMIBConformance 1}
cpaeMIBGroups OBJECT IDENTIFIER ::= {cpaeMIBConformance 2}

-- Conformance 

cpaeCompliance MODULE-COMPLIANCE
    STATUS     deprecated
    DESCRIPTION
        "The compliance statement."
    MODULE
        MANDATORY-GROUPS {
            cpaeMultipleHostGroup
        }
    ::= {cpaeMIBCompliances 1}

cpaeCompliance2 MODULE-COMPLIANCE
    STATUS     current
    DESCRIPTION
        "The compliance statement for devices that implement
         the CISCO-PAE-MIB."
    MODULE
        MANDATORY-GROUPS {
            cpaePortEntryGroup
        }

    GROUP    cpaeGuestVlanGroup
    DESCRIPTION
        "This group is mandatory in devices running software
         which supports Guest Vlan feature."

    ::= {cpaeMIBCompliances 2}

-- Units of Conformance

cpaeMultipleHostGroup    OBJECT-GROUP
    OBJECTS {
        cpaeMultipleHost
    }
    STATUS    deprecated
    DESCRIPTION    
        "A collection of objects that provide the multiple 
        host configuration information for a PAE port.  
        These are additional to the IEEE Std 802.1x PAE MIB."
    ::= {cpaeMIBGroups 1}

cpaePortEntryGroup OBJECT-GROUP
    OBJECTS {
        cpaePortMode
    }
    STATUS    current
    DESCRIPTION
        "A collection of objects that provides the port-mode
         configuration for a PAE port."
    ::= {cpaeMIBGroups 2}

cpaeGuestVlanGroup       OBJECT-GROUP
    OBJECTS {
        cpaeGuestVlanId
    }
    STATUS    current
    DESCRIPTION
        "A collection of objects that provides the Guest Vlan
         configuration information for the system."
    ::= {cpaeMIBGroups 3}
END
