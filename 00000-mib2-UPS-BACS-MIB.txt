BACS-MIB DEFINITIONS ::= BEGIN

   IMPORTS
       MODULE-IDENTITY, OBJECT-TYPE, NOTIFICATION-TYPE,
       OBJECT-IDENTITY, Counter32, Gauge32, Integer32
           FROM SNMPv2-SMI
       DisplayString, TimeStamp, AutonomousType
           FROM SNMPv2-TC
       MODULE-COMPLIANCE, OBJECT-GROUP
           FROM SNMPv2-CONF;

   PositiveInteger ::= TEXTUAL-CONVENTION
       DISPLAY-HINT "d"
       STATUS       current
       DESCRIPTION
               "This data type is a non-zero and non-negative value."
       SYNTAX       INTEGER (1..2147483647)

   NonNegativeInteger ::= TEXTUAL-CONVENTION
       DISPLAY-HINT "d"
       STATUS       current
       DESCRIPTION
               "This data type is a non-negative value."
       SYNTAX       INTEGER (0..2147483647)

   org         OBJECT IDENTIFIER ::= { iso 3 }  --  "iso" = 1
   dod         OBJECT IDENTIFIER ::= { org 6 }
   internet    OBJECT IDENTIFIER ::= { dod 1 }
   mgmt        OBJECT IDENTIFIER ::= { internet 2 }
   mib-2       OBJECT IDENTIFIER ::= { mgmt 1 }
   upsMIB      OBJECT IDENTIFIER ::= { mib-2 33 }
   bacs        OBJECT IDENTIFIER ::= { upsMIB 4 }

   --
   -- BACS Settings
   --

   bacsSettings OBJECT IDENTIFIER ::= { bacs 1 }

   bacsModuleType OBJECT-TYPE
       SYNTAX      INTEGER {
           RTVC001 (1),
           RTVC002 (2),
           RTVC003 (3),
           RTVC004 (4),
           RTVC0016Volt (5),
           RTVC0026Volt (6),
           RTVC0036Volt (7),
           RTVC0046Volt (8),
       }
       MAX-ACCESS  read-only
       STATUS      current
       DESCRIPTION "BACS Module Type."
       ::= { bacsSettings 1 }

   bacsNumStrings OBJECT-TYPE
       SYNTAX      NonNegativeInteger
       UNITS       "strings"
       MAX-ACCESS  read-only
       STATUS      current
       DESCRIPTION "Number of battery strings."
       ::= { bacsSettings 2 }

   bacsNumModules OBJECT-TYPE
       SYNTAX      NonNegativeInteger
       UNITS       "batteries"
       MAX-ACCESS  read-only
       STATUS      current
       DESCRIPTION "Total number of batteries."
       ::= { bacsSettings 3 }

   bacsBattCap OBJECT-TYPE
       SYNTAX      PositiveInteger
       UNITS       "Ah"
       MAX-ACCESS  read-only
       STATUS      current
       DESCRIPTION "Capacity of installed batteries."
       ::= { bacsSettings 4 }

   bacsLogRate1 OBJECT-TYPE
       SYNTAX      PositiveInteger
       UNITS       "seconds"
       MAX-ACCESS  read-only
       STATUS      current
       DESCRIPTION "Lograte during normal operation."
       ::= { bacsSettings 5 }

   bacsLogRate2 OBJECT-TYPE
       SYNTAX      PositiveInteger
       UNITS       "seconds"
       MAX-ACCESS  read-only
       STATUS      current
       DESCRIPTION "Lograte during charge or discharge."
       ::= { bacsSettings 6 }

   bacsResistPollRate OBJECT-TYPE
       SYNTAX      PositiveInteger
       UNITS       "minutes"
       MAX-ACCESS  read-write
       STATUS      current
       DESCRIPTION "Pollrate internal resistance."
       ::= { bacsSettings 7 }

   bacsBattAlarmLevel OBJECT-TYPE
       SYNTAX      PositiveInteger
       UNITS       "mOhm"
       MAX-ACCESS  read-write
       STATUS      current
       DESCRIPTION "Resistane alarm level."
       ::= { bacsSettings 8 }

   bacsBattWarnLevel OBJECT-TYPE
       SYNTAX      PositiveInteger
       UNITS       "mOhm"
       MAX-ACCESS  read-write
       STATUS      current
       DESCRIPTION "Resistane warnig level."
       ::= { bacsSettings 9 }

   bacsTemperatureLowAlarm OBJECT-TYPE
       SYNTAX      PositiveInteger
       UNITS       "0.1 deg celsius"
       MAX-ACCESS  read-write
       STATUS      current
       DESCRIPTION "Temperature alarm below this level."
       ::= { bacsSettings 10 }

   bacsTemperatureHighAlarm OBJECT-TYPE
       SYNTAX      PositiveInteger
       UNITS       "0.1 deg celsius"
       MAX-ACCESS  read-write
       STATUS      current
       DESCRIPTION "Temperature alarm above this level."
       ::= { bacsSettings 11 }

   bacsVoltageLowAlarm OBJECT-TYPE
       SYNTAX      PositiveInteger
       UNITS       "0.1 volt"
       MAX-ACCESS  read-write
       STATUS      current
       DESCRIPTION "Voltage alarm below this level."
       ::= { bacsSettings 12 }

   bacsVoltageHighAlarm OBJECT-TYPE
       SYNTAX      PositiveInteger
       UNITS       "0.1 volt"
       MAX-ACCESS  read-write
       STATUS      current
       DESCRIPTION "Voltage alarm above this level."
       ::= { bacsSettings 13 }


   --
   -- BACS Objects
   --

   bacsObjects   OBJECT IDENTIFIER ::= { bacs 2 }

   bacsEndVolt OBJECT-TYPE
       SYNTAX      PositiveInteger
       UNITS       "0.1 Volt"
       MAX-ACCESS  read-only
       STATUS      current
       DESCRIPTION "Charge end voltage."
       ::= { bacsObjects 1 }

   bacsAvModuleVolt OBJECT-TYPE
       SYNTAX      PositiveInteger
       UNITS       "0.1 Volt"
       MAX-ACCESS  read-only
       STATUS      current
       DESCRIPTION "Average module voltage."
       ::= { bacsObjects 2 }

   bacsTotalVolt OBJECT-TYPE
       SYNTAX      PositiveInteger
       UNITS       "0.1 Volt"
       MAX-ACCESS  read-only
       STATUS      current
       DESCRIPTION "Total voltage of all modules."
       ::= { bacsObjects 3 }

   bacsNumModules OBJECT-TYPE
       SYNTAX      NonNegativeInteger
       MAX-ACCESS  read-only
       STATUS      current
       DESCRIPTION "The number of installed battery modules."
       ::= { bacsObjects 4 }

   bacsModuleTable    OBJECT-TYPE
       SYNTAX      SEQUENCE OF bacsEntry
       MAX-ACCESS  not-accessible
       STATUS      current
       DESCRIPTION "The list of battery table entries."
       ::= { bacsObjects 5 }

   bacsModuleEntry  OBJECT-TYPE
       SYNTAX      bacsEntry
       MAX-ACCESS  not-accessible
       STATUS      current
       DESCRIPTION "An entry containing information applicable to a particular battery."
       INDEX       { bacsModuleIndex }
       ::= { bacsModuleTable 1 }

   bacsEntry ::= SEQUENCE {
       bacsModuleIndex         PositiveInteger,
       bacsModuleVoltage       PositiveInteger,
       bacsModuleTemperature   PositiveInteger,
       bacsModuleBypass        NonNegativeInteger,
       bacsModuleResitance     NonNegativeInteger,
       bacsModuleState         NonNegativeInteger
   }

   bacsModuleIndex OBJECT-TYPE
       SYNTAX      PositiveInteger
       MAX-ACCESS  not-accessible
       STATUS      current
       DESCRIPTION "The module identifier."
       ::= { bacsModuleEntry 1 }

   bacsModuleVoltage OBJECT-TYPE
       SYNTAX      PositiveInteger
       UNITS       "0.1 volt"
       MAX-ACCESS  read-only
       STATUS      current
       DESCRIPTION "The module voltage."
       ::= { bacsModuleEntry 2 }

   bacsModuleTemperature OBJECT-TYPE
       SYNTAX      PositiveInteger
       UNITS       "degrees celcius"
       MAX-ACCESS  read-only
       STATUS      current
       DESCRIPTION "The module voltage."
       ::= { bacsModuleEntry 3 }

   bacsModuleBypass OBJECT-TYPE
       SYNTAX      NonNegativeInteger
       UNITS       "0.1 percent"
       MAX-ACCESS  read-only
       STATUS      current
       DESCRIPTION "The module voltage."
       ::= { bacsModuleEntry 4 }

   bacsModuleResitance OBJECT-TYPE
       SYNTAX      NonNegativeInteger
       UNITS       "0.1 mOhm"
       MAX-ACCESS  read-only
       STATUS      current
       DESCRIPTION "The module voltage."
       ::= { bacsModuleEntry 5 }

   bacsModuleState OBJECT-TYPE
       SYNTAX      NonNegativeInteger
       MAX-ACCESS  read-only
       STATUS      current
       DESCRIPTION "The module voltage."
       ::= { bacsModuleEntry 6 }


   --
   -- BACS Alarms
   --

   bacsAlarms   OBJECT IDENTIFIER ::= { bacs 3 }

   bacsAlarmsPresent OBJECT-TYPE
       SYNTAX      Gauge32
       MAX-ACCESS  read-only
       STATUS      current
       DESCRIPTION "The present number of active alarm conditions."
       ::= { bacsAlarms 1 }
   
   bacsAlarmTable OBJECT-TYPE
       SYNTAX      SEQUENCE OF bacsAlarm
       MAX-ACCESS  not-accessible
       STATUS      current
       DESCRIPTION "A list of alarm entries."
       ::= { bacsAlarms 2 }
   
   bacsAlarmEntry OBJECT-TYPE
       SYNTAX      bacsAlarm
       MAX-ACCESS  not-accessible
       STATUS      current
       DESCRIPTION "An entry containing information applicable to a particular alarm."
       INDEX      { bacsAlarmId }
       ::= { bacsAlarmTable 1 }
   
   bacsAlarm ::= SEQUENCE {
       bacsAlarmId          PositiveInteger,
       bacsAlarmDescr       AutonomousType,
       bacsAlarmTime        TimeStamp
   }
   
   bacsAlarmId OBJECT-TYPE
       SYNTAX      PositiveInteger
       MAX-ACCESS  read-only
       STATUS      current
       DESCRIPTION "A unique identifier for an alarm condition. This value must remain constant."
       ::= { bacsAlarmEntry 1 }
   
   bacsAlarmDescr OBJECT-TYPE
       SYNTAX      AutonomousType
       MAX-ACCESS  read-only
       STATUS      current
       DESCRIPTION "A reference to an alarm description object. The object referenced should not be
                 accessible, but rather be used to provide a unique description of the alarm   condition."
       ::= { bacsAlarmEntry 2 }
   
   bacsAlarmTime OBJECT-TYPE
       SYNTAX      TimeStamp
       MAX-ACCESS  read-only
       STATUS      current
       DESCRIPTION "The value of sysUpTime when the alarm condition was detected. If the alarm
               condition was detected at the time of agent startup and presumably existed before
               agent startup, the value of dcAlarmTime shall equal 0."
       ::= { bacsAlarmEntry 3 }

   bacsWellKnownAlarms OBJECT IDENTIFIER ::= { bacsAlarms 3 }

   bacsAlarmSystemError OBJECT-IDENTITY
       STATUS      current
       DESCRIPTION "This object indicates a communication problem from the agent to one or more of the battery modules."
       ::= { bacsWellKnownAlarms  1 }
       
   bacsAlarmResistWarn OBJECT-IDENTITY
       STATUS      current
       DESCRIPTION "This object indicates that the internal restiance of one or more batteries is above the warning level."
       ::= { bacsWellKnownAlarms  2 }

   bacsAlarmResistAlarm OBJECT-IDENTITY
       STATUS      current
       DESCRIPTION "This object indicates that the internal restiance of one or more batteries is above the alarm level."
       ::= { bacsWellKnownAlarms  3 }

   bacsAlarmVoltage OBJECT-IDENTITY
       STATUS      current
       DESCRIPTION "This object indicates that the voltage of one or more batteries is outside the defined rage."
       ::= { bacsWellKnownAlarms  4 }

   bacsAlarmTemperature OBJECT-IDENTITY
       STATUS      current
       DESCRIPTION "This object indicates that the temperature of one or more batteries is outside the defined rage."
       ::= { bacsWellKnownAlarms  5 }


   --
   -- BACS Traps
   --

   bacsTraps   OBJECT IDENTIFIER ::= { bacs 4 }

   bacsTrapAlarmEntryAdded NOTIFICATION-TYPE
       OBJECTS { bacsAlarmId, bacsAlarmDescr }
       STATUS      current
       DESCRIPTION "This trap is sent upon a alarm in the system appears."
       ::= { bacsTraps 1 }

   bacsTrapAlarmEntryRemoved NOTIFICATION-TYPE
       OBJECTS { bacsAlarmId, bacsAlarmDescr }
       STATUS      current
       DESCRIPTION "This trap is sent upon a alarm in the system disappears."
       ::= { bacsTraps 2 }


   END
