NetWare-Server-Trend-MIB DEFINITIONS ::= BEGIN

       --
       -- This MIB document is 'WORK IN PROGRESS' of Novell, Inc.
       -- As such, it is subject to change, without notice, until
       -- such time as it is formally released and this disclaimer
       -- removed.
       --
       --
       -- Last Update: January 10, 1995
       --

       IMPORTS
          enterprises
             FROM RFC1155-SMI

          InternationalDisplayString
             FROM HOST-RESOURCES-MIB

          OBJECT-TYPE
             FROM RFC-1212

          TRAP-TYPE
             FROM RFC-1215;


       novell         OBJECT IDENTIFIER ::= { enterprises 23 }
       mibDoc         OBJECT IDENTIFIER ::= { novell 2 }
       nwTrend   OBJECT IDENTIFIER ::= { mibDoc 26 }

       nwtControl     OBJECT IDENTIFIER ::= { nwTrend 1 }
       nwtTrapInfo    OBJECT IDENTIFIER ::= { nwTrend 2 }


       -- The date and time Universal Coordinated Time (UTC);
       -- represented as the number of seconds since midnight on
       -- January 1, 1970.
       --
       NWTime    ::= INTEGER (0..2147483647)
--       Seconds        ::= INTEGER (0..2147483647)


       --
       -- The Control Group
       --

       nwtControlTable OBJECT-TYPE
          SYNTAX SEQUENCE OF NwtControlEntry
          ACCESS not-accessible
          STATUS mandatory
          DESCRIPTION
                 "A list of data table entries"
          ::= { nwtControl 1 }

       nwtControlEntry OBJECT-TYPE
          SYNTAX NwtControlEntry
          ACCESS not-accessible
          STATUS mandatory
          DESCRIPTION
                 "A list of parameters that describe the thresholds and
                 trends being performed."
          INDEX  { nwtControlAttributeClass, nwtControlIndex }
          ::= { nwtControlTable 1 }

       NwtControlEntry ::= SEQUENCE {
            nwtControlAttributeClass         INTEGER,
            nwtControlIndex                  INTEGER,
            nwtControlAttributeInstance      InternationalDisplayString,
            nwtControlSampleInterval         INTEGER,
            nwtControlSampleType             INTEGER,
            nwtControlSampleInvalidValue     INTEGER,
            nwtControlLastSampleValue        INTEGER,
            nwtControlReferenceTimeStamp     NWTime,
            nwtControlThresholdState         INTEGER,
            nwtControlThresholdType          INTEGER,
            nwtControlRisingThreshold        INTEGER,
            nwtControlFallingThreshold       INTEGER,
            nwtControlHistoryState           INTEGER,
            nwtControlHistoryLastSampleIndex INTEGER,
            nwtControlHistoryBucketsRequested  INTEGER,
            nwtControlHistoryBucketsGranted  INTEGER,
            nwtControlStatus                 INTEGER
          }

       nwtControlAttributeClass OBJECT-TYPE
          SYNTAX INTEGER {
                      avgLoggedInUsers(1),
                      avgConnections(2),
                      fileReads(3),
                      fileWrites(4),
                      fileReadKBytes(5),
                      fileWriteKBytes(6),
                      lslInPackets(7),
                      lslOutPackets(8),
                      ncpRequests(9),
                      pctCpuUtilization(10),
                      pctCacheBuffers(11),
                      pctCodeAndDataMemory(12),
                      pctAllocatedMemory(13),
                      pctDirtyCacheBuffers(14),
                      physIfInPackets(15),
                      physIfOutPackets(16),
                      physIfInKBytes(17),
                      physIfOutKBytes(18),
                      queueAvgNumReadyJobs(19),
                      queueAvgNumReadyKBytes(20),
                      queueAvgNextJobWaitTime(21),
                      volumePctFreeSpace(22),
                      pctCacheHitRate(23),
                      diskPctFreeRedirectionArea(24)
                 }
          ACCESS read-only
          STATUS mandatory
          DESCRIPTION
                 "An enumeration which identifies the attribute being
                 monitored.  See also the definition of the
                 corresponding trap.

                 The pctCpuUtilization is monitored for each CPU in the
                 server.

                 The attributes whose name starts with 'physIf', are
                 monitored for each physical network interface on the
                 server.

                 The attributes whose name starts with 'queue', are
                 monitored for each queue on the server.

                 The attributes whose name starts with 'volume', are
                 monitored for each volume on the server.

                 The attributes whose name starts with 'disk' are

                 monitored for each disk on the server.

                 All other attributes have a single instance."
          ::= { nwtControlEntry 1 }

       nwtControlIndex OBJECT-TYPE
          SYNTAX INTEGER (1..2147483647)
          ACCESS read-only
          STATUS mandatory
          DESCRIPTION
                 "An index to be used to access the nwtHistoryTable to
                 retrieve the stored samples for this variable.  This
                 value must remain constant at least from one re-
                 initialization of the agent to the next re-
                 initialization."
          ::= { nwtControlEntry 2 }

       nwtControlAttributeInstance OBJECT-TYPE
          SYNTAX InternationalDisplayString
          ACCESS read-only
          STATUS mandatory
          DESCRIPTION
                 "A printable string which uniquely, and permanently,
                 identifies one particular 'instance' of the attribute.

                 For example, if nwtControlAttributeClass specifies an
                 attribute of a NetWare volume,
                 nwtControlAttributeInstance will specify the volume to
                 which this particular instance pertains.

                 A zero-length string will be returned if the attribute
                 can not have multiple instances."
          ::= { nwtControlEntry 3 }

       nwtControlSampleInterval OBJECT-TYPE
          SYNTAX INTEGER {
                      fiveSeconds(1),
                      tenSeconds(2),
                      fifteenSeconds(3),
                      thirtySeconds(4),
                      oneMinute(5),
                      fiveMinutes(6),
                      fifteenMinutes(7),
                      thirtyMinutes(8),
                      oneHour(9),
                      fourHours(10),
                      eightHours(11),
                      oneDay(12)
                 }
          ACCESS read-write
          STATUS mandatory
          DESCRIPTION
                 "An enumeration which identifies the interval over
                 which the data is sampled, compared with the rising and
                 falling thresholds, and saved in the history.

                 Intervals will be aligned to the real world clock.  For
                 instance, hourly samples will be taken on the hour, 15-
                 minute samples will be taken at n:00, n:15, n:30, and
                 n:45, etc.

                 If a valid sample can not be taken for any reason
                 (server down, excessive timer skew, etc.) then the
                 sample value will be set to the invalid value.
                 If the interval is changed, any associated history will
                 be discarded and a new history collection commenced."
          ::= { nwtControlEntry 4 }

       nwtControlSampleType OBJECT-TYPE
          SYNTAX INTEGER {
                      absoluteValue(1),
                      deltaValue(2),
                      averageValue(3)
                 }
          ACCESS read-only
          STATUS mandatory
          DESCRIPTION
                 "The method of sampling the selected variable and
                 calculating the value to be compared against the
                 thresholds.

                 If the value of this object is 'absoluteValue', the
                 value of the selected variable at the end of the
                 sampling interval will be compared directly with both
                 the nwtControlRisingThreshold and the
                 nwtControlFallingThreshold values.

                 If the value of this object is 'deltaValue', the value
                 of the selected variable at the end of the sampling
                 interval will be subtracted from its value at the end
                 of the previous sampling interval, and the difference
                 compared with both the nwtControlRisingThreshold and
                 the nwtControlFallingThreshold values.

                 If the value of this object is 'averageValue', the
                 average value of the selected variable over the
                 sampling interval will be compared with both the
                 nwtControlRisingThreshold and the
                 nwtControlFallingThreshold values.
                 "
          ::= { nwtControlEntry 5 }

       nwtControlSampleInvalidValue OBJECT-TYPE
          SYNTAX INTEGER
          ACCESS read-only
          STATUS mandatory
          DESCRIPTION
                 "The value used to represent 'invalid' for this
                 variable.  Any sample of this variable having a value
                 equal to the value of nwtControlSampleInvalidValue is
                 not a valid sample and should be treated accordingly."
          ::= { nwtControlEntry 6 }

       nwtControlLastSampleValue OBJECT-TYPE
          SYNTAX INTEGER
          ACCESS read-only
          STATUS mandatory
          DESCRIPTION
                 "The value of the variable during the last sampling
                 period.  The value during the current sampling period
                 is not made available until the period is completed.

                 Note that if the associated value nwtControlSampleType
                 is set to 'deltaValue', the value of this object is the
                 difference in the sampled variable since the last
                 sample.  If the value of nwtControlSampleType is
                 'averageValue', the value of this object is the average
                 value of the selected variable over the sampling
                 interval."
          ::= { nwtControlEntry 7 }

       nwtControlReferenceTimeStamp OBJECT-TYPE
          SYNTAX NWTime
          ACCESS read-only
          STATUS mandatory
          DESCRIPTION
                 "The absolute date and time (UTC) of the beginning of
                 the history associated with this control entry,
                 expressed as seconds since midnight on January 1, 1970.
                 The timestamp of any sample in the history may be
                 computed as follows:

                  nwtControlReferenceTimeStamp
                  + (nwtHistorySampleIndex * intervalInSeconds)

                 A value of 0 indicates that there is no history
                 available for this variable."
          ::= { nwtControlEntry 8 }

       nwtControlThresholdState OBJECT-TYPE
          SYNTAX INTEGER {
                      enabled(1),
                      disabled(2)
                 }
          ACCESS read-write
          STATUS mandatory
          DESCRIPTION
                 "The current state of threshold monitoring for this
                 nwtControlEntry.

                 When the state is 'enabled', the sampled value will be
                 compared to the appropriate threshold, and a trap
                 generated if appropriate.

                 When the state is 'disabled', the thresholds will be
                 ignored, and no trap will ever be generated."
          ::= { nwtControlEntry 9 }

       nwtControlThresholdType OBJECT-TYPE
          SYNTAX INTEGER {
                      risingAlarm(1),
                      fallingAlarm(2)
                 }
          ACCESS read-only
          STATUS mandatory
          DESCRIPTION
                 "An enumeration that indicates whether a trap is to be
                 generated when the sampled variable rises to the
                 nwtControlRisingThreshold, or when it falls to the
                 nwtControlFallingThreshold."
          ::= { nwtControlEntry 10 }

       nwtControlRisingThreshold OBJECT-TYPE
          SYNTAX INTEGER
          ACCESS read-write
          STATUS mandatory
          DESCRIPTION
                 "A threshold for the sampled variable.  When the
                 current sampled value is greater than or equal to this
                 threshold, and the value at the last sampling interval
                 was less than this threshold, and the value of
                 nwtControlThresholdType is 'risingAlarm', a single trap
                 will be generated.

                 After a a trap is generated, another such trap will not

                 be generated until the sampled value falls below this
                 threshold and reaches the nwtControlFallingThreshold."
          ::= { nwtControlEntry 11 }

       nwtControlFallingThreshold OBJECT-TYPE
          SYNTAX INTEGER
          ACCESS read-write
          STATUS mandatory
          DESCRIPTION
                 "A threshold for the sampled variable.  When the
                 current sampled value is less than or equal to this
                 threshold, and the value at the last sampling interval
                 was greater than this threshold, and the value of
                 nwtControlThresholdType is 'fallingAlarm', a single
                 trap will be generated.

                 After a trap is generated, another such trap will not
                 be generated until the sampled value rises above this
                 threshold and reaches the nwtControlRisingThreshold."
          ::= { nwtControlEntry 12 }

       nwtControlHistoryState OBJECT-TYPE
          SYNTAX INTEGER {
                      enabled(1),
                      disabled(2)
                 }
          ACCESS read-write
          STATUS mandatory
          DESCRIPTION
                 "The current state of history collection for this
                 nwtControlEntry.

                 When the state is 'enabled', each sampled value will be
                 added to the history.

                 When the state is 'disabled', sampled values will not
                 be added to the stored history."
          ::= { nwtControlEntry 13 }

       nwtControlHistoryLastSampleIndex OBJECT-TYPE
          SYNTAX INTEGER (0..2147483647)
          ACCESS read-only
          STATUS mandatory
          DESCRIPTION
                 "The value of nwtHistorySampleIndex for the most recent
                 sample in the associated history.

                 A value of 0 indicates that there is no history
                 available for this variable."
          ::= { nwtControlEntry 14 }

       nwtControlHistoryBucketsRequested OBJECT-TYPE
          SYNTAX INTEGER (0..2147483647)
          ACCESS read-write
          STATUS mandatory
          DESCRIPTION
                 "The requested number of discrete sampling intervals
                 over which data should be saved in the part of the
                 nwtHistoryTable associated with this sampled variable.

                 When this object is modified, the agent should set
                 nwtControlHistoryBucketsGranted as closely to this
                 object as is possible for the particular agent
                 implementation, the local policy, and available
                 resources.  If the size of the history is increased, no
                 history data will be lost.  If the size of the history
                 is decreased, the oldest samples will be discarded as
                 necessary."
          ::= { nwtControlEntry 15 }

       nwtControlHistoryBucketsGranted OBJECT-TYPE
          SYNTAX INTEGER (0..2147483647)
          ACCESS read-only
          STATUS mandatory
          DESCRIPTION
                 "The number of discrete sampling intervals over which
                 data shall be saved in the part of the nwtHistoryTable
                 associated with this sampled variable.

                 There will be times when the actual number of buckets
                 associated with this entry is less than the value of
                 this object.  In this case, at the end of each sampling
                 interval, a new bucket will be added to the part of the
                 nwtHistoryTable associated with this nwtControlEntry.

                 When the number of buckets reaches the value of this
                 object and a new bucket is to be added to the part of
                 the nwtHistoryTable associated with this
                 nwtControlEntry, the oldest bucket associated with this
                 nwtControlEntry shall be deleted by the agent so that
                 the new bucket can be added."
          ::= { nwtControlEntry 16 }

       nwtControlStatus OBJECT-TYPE
          SYNTAX INTEGER {
                      valid(1),
                      invalid(2)
                 }
          ACCESS read-only
          STATUS mandatory
          DESCRIPTION
                 "The current status of the attribute instance monitored
                 by this nwtControlEntry.

                 As new volumes, disks, adapters, etc. are added to the
                 server, entries for the new instances of each monitored
                 attribute will automatically be added to this table,
                 using appropriate default values for thresholds etc.
                 From time-to-time, volumes, disks, adapters, etc. may
                 also be permanently removed from the server; however,
                 the entries for those instances in this table, and any
                 associated histories, will continue to exist.

                 A value of 'valid' indicates that the instance defined
                 by this nwtControlEntry is present in the server.

                 A value of 'invalid' indicates that the instance
                 defined by this nwtControlEntry is no longer present in
                 the server.  Any associated history data is still
                 available."
          ::= { nwtControlEntry 17 }


       --
       -- History Table
       --

       nwtHistoryTable OBJECT-TYPE
          SYNTAX SEQUENCE OF NwtHistoryEntry
          ACCESS not-accessible
          STATUS mandatory
          DESCRIPTION
                 "A list of history data sample entries"
          ::= { nwtControl 2 }

       nwtHistoryEntry OBJECT-TYPE
          SYNTAX NwtHistoryEntry
          ACCESS not-accessible
          STATUS mandatory
          DESCRIPTION
                 "An historical sample of the variable defined in the
                 corresponding nwtControlEntry, which set up the
                 parameters for a regular collection of these samples"
          INDEX  { nwtHistoryControlIndex, nwtHistorySampleIndex }
          ::= { nwtHistoryTable 1 }

       NwtHistoryEntry ::= SEQUENCE {
            nwtHistoryControlIndex           INTEGER,
            nwtHistorySampleIndex            INTEGER,
            nwtHistorySampleValue            INTEGER
          }

       nwtHistoryControlIndex OBJECT-TYPE
          SYNTAX INTEGER (1..2147483647)
          ACCESS read-only
          STATUS mandatory
          DESCRIPTION
                 "The history of which this entry is a part.  The
                 history identified by a particular value of this index
                 is the same history as identified by the same value of
                 nwtControlIndex."
          ::= { nwtHistoryEntry 1 }

       nwtHistorySampleIndex OBJECT-TYPE
          SYNTAX INTEGER (1..2147483647)
          ACCESS read-only
          STATUS mandatory
          DESCRIPTION
                 "An index that uniquely identifies the particular
                 sample this entry represents among all samples
                 associated with the same nwtControlEntry.  This index
                 starts at 1 and increases by one as each interval
                 passes.  For periods when the server is down, or the
                 agent is not running, the corresponding value of
                 nwtHistorySampleValue will be equal to the value of
                 nwtControlSampleInvalidValue.  The timestamp of any
                 sample in the history may be computed as follows:

                 nwtControlReferenceTimeStamp
                  + (nwtHistorySampleIndex * intervalInSeconds)"
          ::= { nwtHistoryEntry 2 }

       nwtHistorySampleValue OBJECT-TYPE
          SYNTAX INTEGER
          ACCESS read-only
          STATUS mandatory
          DESCRIPTION
                 "The value of the monitored object at the time the
                 sample was taken."
          ::= { nwtHistoryEntry 3 }
       --
       -- The Trap Info Group
       --
       --
       -- The objects in this group exist solely for use as
       -- var-binds in traps.  They are not-accessible as objects
       -- in their own right.
       --

       nwtServerName OBJECT-TYPE
          SYNTAX InternationalDisplayString (SIZE(0..48))
          ACCESS not-accessible
          STATUS mandatory
          DESCRIPTION
                 "The physical name of this server"
          ::= { nwtTrapInfo 1 }

       nwtTrapTime OBJECT-TYPE
          SYNTAX NWTime
          ACCESS not-accessible
          STATUS mandatory
          DESCRIPTION
                 "The time in seconds since midnight January 1st 1970
                 Universal Coordinated Time UTC."
          ::= { nwtTrapInfo 2 }

       nwtThreshold OBJECT-TYPE
          SYNTAX INTEGER
          ACCESS not-accessible
          STATUS mandatory
          DESCRIPTION
                 "The threshold value that has been exceeded."
          ::= { nwtTrapInfo 3 }

       nwtInterval OBJECT-TYPE
          SYNTAX INTEGER
--          SYNTAX Seconds  Edited for use on HPOV, replaced with INTEGER
          ACCESS not-accessible
          STATUS mandatory
          DESCRIPTION
                 "The sample interval in seconds."
          ::= { nwtTrapInfo 4 }

       nwtInterfaceName OBJECT-TYPE
          SYNTAX InternationalDisplayString (SIZE(0..64))
          ACCESS not-accessible
          STATUS mandatory
          DESCRIPTION
                 "The name of the physical interface."
          ::= { nwtTrapInfo 5 }

       nwtQueueName OBJECT-TYPE
          SYNTAX InternationalDisplayString
          ACCESS not-accessible
          STATUS mandatory
          DESCRIPTION
                 "The name of the queue."
          ::= { nwtTrapInfo 6 }

       nwtVolumeName OBJECT-TYPE
          SYNTAX InternationalDisplayString (SIZE(0..64))
          ACCESS not-accessible
          STATUS mandatory
          DESCRIPTION
                 "The physical name of the volume."
          ::= { nwtTrapInfo 7 }
       nwtDiskName OBJECT-TYPE
          SYNTAX InternationalDisplayString (SIZE(0..64))
          ACCESS not-accessible
          STATUS mandatory
          DESCRIPTION
                 "The name of the disk."
          ::= { nwtTrapInfo 8 }

       nwtCPUDescription OBJECT-TYPE
          SYNTAX InternationalDisplayString
          ACCESS not-accessible
          STATUS mandatory
          DESCRIPTION
                 "The processor description."
          ::= { nwtTrapInfo 9 }
       --
       -- Traps
       --

       nwtThresholdLoggedInUsers TRAP-TYPE
          ENTERPRISE   nwTrend
          VARIABLES    {
                       nwtServerName, nwtTrapTime, nwtThreshold,
                       nwtInterval
                       }
          DESCRIPTION
                 "The average number of logged in users exceeded the
                 threshold"
          --#TYPE      "Threshold - logged-in users"
          --#SUMMARY   "Avg.# of logged-in users exceeded "
          --#SUMMARY   "threshold of %d for a %d second interval "
          --#SUMMARY   "on server %s."
          --#ARGUMENTS { 2, 3, 0 }
          --#SEVERITY  INFORMATIONAL
          --#TIMEINDEX 1
          --#HELP      "nwtrend.hlp"
          --#HELPTAG   1
          --#STATE     OPERATIONAL
          ::= 1

       nwtThresholdConnections  TRAP-TYPE
          ENTERPRISE   nwTrend
          VARIABLES    {
                       nwtServerName, nwtTrapTime, nwtThreshold,
                       nwtInterval
                       }
          DESCRIPTION
                 "The average number of connections exceeded the
                 threshold"
          --#TYPE      "Threshold - connections"
          --#SUMMARY   "Avg.# of connections exceeded"
          --#SUMMARY   "threshold of %d for a %d second interval "
          --#SUMMARY   "on server %s."
          --#ARGUMENTS { 2, 3, 0 }
          --#SEVERITY  INFORMATIONAL
          --#TIMEINDEX 1
          --#HELP      "nwtrend.hlp"
          --#HELPTAG   2
          --#STATE     OPERATIONAL
          ::= 2

       nwtThresholdFileReads TRAP-TYPE
          ENTERPRISE   nwTrend
          VARIABLES    {
                       nwtServerName, nwtTrapTime, nwtThreshold,
                       nwtInterval
                       }
          DESCRIPTION
                 "The number of file system reads exceeded the
                 threshold"
          --#TYPE      "Threshold - file system reads"
          --#SUMMARY   "Number of file system reads exceeded "
          --#SUMMARY   "threshold of %d in a %d second interval "
          --#SUMMARY   "on server %s."
          --#ARGUMENTS { 2, 3, 0 }
          --#SEVERITY  INFORMATIONAL
          --#TIMEINDEX 1
          --#HELP      "nwtrend.hlp"
          --#HELPTAG   3
          --#STATE     OPERATIONAL
          ::= 3

       nwtThresholdFileWrites TRAP-TYPE
          ENTERPRISE   nwTrend
          VARIABLES    {
                       nwtServerName, nwtTrapTime, nwtThreshold,
                       nwtInterval
                       }
          DESCRIPTION
                 "The number of file system writes exceeded the
                 threshold"
          --#TYPE      "Threshold - file system writes"
          --#SUMMARY   "Number of file system writes exceeded "
          --#SUMMARY   "threshold of %d in a %d second interval "
          --#SUMMARY   "on server %s."
          --#ARGUMENTS { 2, 3, 0 }
          --#SEVERITY  INFORMATIONAL
          --#TIMEINDEX 1
          --#HELP      "nwtrend.hlp"
          --#HELPTAG   4
          --#STATE     OPERATIONAL
          ::= 4

       nwtThresholdFileReadKBytes TRAP-TYPE
          ENTERPRISE   nwTrend
          VARIABLES    {
                       nwtServerName, nwtTrapTime, nwtThreshold,
                       nwtInterval
                       }
          DESCRIPTION
                 "The number of KBytes read from file system  exceeded
                 the threshold"
          --#TYPE      "Threshold - file system KBytes read"
          --#SUMMARY   "Number of bytes read from file system "
          --#SUMMARY   "exceeded threshold of %d KB in a %d "
          --#SUMMARY    "second interval on server %s."
          --#ARGUMENTS { 2, 3, 0 }
          --#SEVERITY  INFORMATIONAL
          --#TIMEINDEX 1
          --#HELP      "nwtrend.hlp"
          --#HELPTAG   5
          --#STATE     OPERATIONAL
          ::= 5

       nwtThresholdFileWriteKBytes TRAP-TYPE
          ENTERPRISE   nwTrend
          VARIABLES    {
                       nwtServerName, nwtTrapTime, nwtThreshold,
                       nwtInterval
                       }
          DESCRIPTION
                 "The number of KBytes written to file system  exceeded
                 the threshold"
          --#TYPE      "Threshold - file system KBytes written"
          --#SUMMARY   "Number of KBytes written to file system "
          --#SUMMARY   "exceeded threshold of %d KB in a %d "
          --#SUMMARY   "second interval on server %s."
          --#ARGUMENTS { 2, 3, 0 }
          --#SEVERITY  INFORMATIONAL
          --#TIMEINDEX 1
          --#HELP      "nwtrend.hlp"
          --#HELPTAG   6
          --#STATE     OPERATIONAL
          ::= 6

       nwtThresholdLslInPackets TRAP-TYPE
          ENTERPRISE   nwTrend
          VARIABLES    {
                       nwtServerName, nwtTrapTime, nwtThreshold,
                       nwtInterval
                       }
          DESCRIPTION
                 "The total packets received by the server exceeded the
                 threshold"
          --#TYPE      "Threshold - total packets received"
          --#SUMMARY   "Total packets received exceeded "
          --#SUMMARY   "threshold of %d in a %d second interval "
          --#SUMMARY   "on server %s."
          --#ARGUMENTS { 2, 3, 0 }
          --#SEVERITY  INFORMATIONAL
          --#TIMEINDEX 1
          --#HELP      "nwtrend.hlp"
          --#HELPTAG   7
          --#STATE     OPERATIONAL
          ::= 7

       nwtThresholdLslOutPackets TRAP-TYPE
          ENTERPRISE   nwTrend
          VARIABLES    {
                       nwtServerName, nwtTrapTime, nwtThreshold,
                       nwtInterval
                       }
          DESCRIPTION
                 "The total packets transmitted by the server exceeded
                 the threshold"
          --#TYPE      "Threshold - total packets transmitted"
          --#SUMMARY   "Total packets transmitted "
          --#SUMMARY   "exceeded threshold of %d in a %d "
          --#SUMMARY   "second interval "
          --#SUMMARY   "on server %s."
          --#ARGUMENTS { 2, 3, 0 }
          --#SEVERITY  INFORMATIONAL
          --#TIMEINDEX 1
          --#HELP      "nwtrend.hlp"
          --#HELPTAG   8
          --#STATE     OPERATIONAL
          ::= 8

       nwtThresholdNcpRequests TRAP-TYPE
          ENTERPRISE   nwTrend
          VARIABLES    {
                       nwtServerName, nwtTrapTime, nwtThreshold,
                       nwtInterval
                       }
          DESCRIPTION
                 "The number of NCPs processed by the server exceeded
                 the threshold"
          --#TYPE      "Threshold - NCP requests processed"
          --#SUMMARY   "NCP requests exceeded "
          --#SUMMARY   "threshold of %d in a %d second interval "
          --#SUMMARY   "on server %s."
          --#ARGUMENTS { 2, 3, 0 }
          --#SEVERITY  INFORMATIONAL
          --#TIMEINDEX 1
          --#HELP      "nwtrend.hlp"
          --#HELPTAG   9
          --#STATE     OPERATIONAL
          ::= 9

       nwtThresholdPctCpuUtilization TRAP-TYPE
          ENTERPRISE   nwTrend
          VARIABLES    {
                        nwtServerName, nwtTrapTime, nwtThreshold,
                       nwtInterval,nwtCPUDescription
                       }
          DESCRIPTION
                 "CPU utilization exceeded the threshold"
          --#TYPE      "Threshold - CPU utilization"
          --#SUMMARY   "CPU utilization exceeded "
          --#SUMMARY   "threshold of %d%% for a %d second "
          --#SUMMARY   "interval on server %s %s."
          --#ARGUMENTS { 2, 3, 0,4 }
          --#SEVERITY  MINOR
          --#TIMEINDEX 1
          --#HELP      "nwtrend.hlp"
          --#HELPTAG   10
          --#STATE     OPERATIONAL
          ::= 10

       nwtThresholdPctCacheBuffers TRAP-TYPE
          ENTERPRISE   nwTrend
          VARIABLES    {
                       nwtServerName, nwtTrapTime, nwtThreshold
                       }
          DESCRIPTION
                 "Cache buffers fell below the threshold"
          --#TYPE      "Threshold - cache buffers"
          --#SUMMARY   "Cache buffers fell below "
          --#SUMMARY   "threshold of %d%% on server %s."
          --#ARGUMENTS { 2, 0 }
          --#SEVERITY  MAJOR
          --#TIMEINDEX 1
          --#HELP      "nwtrend.hlp"
          --#HELPTAG   11
          --#STATE     OPERATIONAL
          ::= 11

       nwtThresholdCodeAndDataMemory TRAP-TYPE
          ENTERPRISE   nwTrend
          VARIABLES    {
                       nwtServerName, nwtTrapTime, nwtThreshold
                       }
          DESCRIPTION
                 "Code and data memory exceeded the threshold"
          --#TYPE      "Threshold - code and data memory"
          --#SUMMARY   "Code and data memory exceeded "
          --#SUMMARY   "threshold of %d%% on server %s."
          --#ARGUMENTS { 2, 0 }
          --#SEVERITY  INFORMATIONAL
          --#TIMEINDEX 1
          --#HELP      "nwtrend.hlp"
          --#HELPTAG   12
          --#STATE     OPERATIONAL
          ::= 12

       nwtThresholdAllocatedMemory TRAP-TYPE
          ENTERPRISE   nwTrend
          VARIABLES    {
                       nwtServerName, nwtTrapTime, nwtThreshold
                       }
          DESCRIPTION
                 "Allocated memory exceeded the threshold"
          --#TYPE      "Threshold - allocated memory"
          --#SUMMARY   "Allocated memory exceeded "
          --#SUMMARY   "threshold of %d%%on server %s."
          --#ARGUMENTS { 2, 0 }
          --#SEVERITY  INFORMATIONAL
          --#TIMEINDEX 1
          --#HELP      "nwtrend.hlp"
          --#HELPTAG   13
          --#STATE     OPERATIONAL
          ::= 13

       nwtThresholdPctDirtyCacheBuffers TRAP-TYPE
          ENTERPRISE   nwTrend
          VARIABLES    {
                       nwtServerName, nwtTrapTime, nwtThreshold,
                       nwtInterval
                       }
          DESCRIPTION
                 "Dirty  Cache buffers exceeded the threshold"
          --#TYPE      "Threshold - dirty cache buffers"
          --#SUMMARY   "Dirty cache buffers exceeded "
          --#SUMMARY   "threshold of %d%% for a %d second "
          --#SUMMARY   "interval on server %s."
          --#ARGUMENTS { 2, 3, 0 }
          --#SEVERITY  MINOR
          --#TIMEINDEX 1
          --#HELP      "nwtrend.hlp"
          --#HELPTAG   14
          --#STATE     OPERATIONAL
          ::= 14

       nwtThresholdPhysIfInPackets TRAP-TYPE
          ENTERPRISE   nwTrend
          VARIABLES    {
                       nwtServerName, nwtTrapTime, nwtThreshold,
                       nwtInterval, nwtInterfaceName
                       }
          DESCRIPTION
                 "The packets received on some physical interface
                 exceeded the threshold"
          --#TYPE      "Threshold - packets received on interface"
          --#SUMMARY   "Packets received on %s exceeded "
          --#SUMMARY   "threshold of %d in a %d second interval "
          --#SUMMARY   "on server %s."
          --#ARGUMENTS { 4, 2, 3, 0 }
          --#SEVERITY  INFORMATIONAL
          --#TIMEINDEX 1
          --#HELP      "nwtrend.hlp"
          --#HELPTAG   15
          --#STATE     OPERATIONAL
          ::= 15

       nwtThresholdPhysIfOutPackets TRAP-TYPE
          ENTERPRISE   nwTrend
          VARIABLES    {
                       nwtServerName, nwtTrapTime, nwtThreshold,
                       nwtInterval, nwtInterfaceName
                       }
          DESCRIPTION
                 "The packets transmitted on some physical interface
                 exceeded the threshold"
          --#TYPE      "Threshold - packets transmitted on interface"
          --#SUMMARY   "Packets transmitted on %s "
          --#SUMMARY   "exceeded threshold of %d in a %d "
          --#SUMMARY   "second interval on server %s."
          --#ARGUMENTS { 4, 2, 3, 0 }
          --#SEVERITY  INFORMATIONAL
          --#TIMEINDEX 1
          --#HELP      "nwtrend.hlp"
          --#HELPTAG   16
          --#STATE     OPERATIONAL
          ::= 16
       nwtThresholdPhysIfInKBytes TRAP-TYPE
          ENTERPRISE   nwTrend
          VARIABLES    {
                       nwtServerName, nwtTrapTime, nwtThreshold,
                       nwtInterval, nwtInterfaceName
                       }
          DESCRIPTION
                 "The total KBytes received on some interface exceeded
                 the threshold"
          --#TYPE      "Threshold - KBytes received interface"
          --#SUMMARY   "KBytes received on %s exceeded "
          --#SUMMARY   "threshold of %dKB in a %d second "
          --#SUMMARY   "interval on server %s."
          --#ARGUMENTS { 4, 2, 3, 0 }
          --#SEVERITY  INFORMATIONAL
          --#TIMEINDEX 1
          --#HELP      "nwtrend.hlp"
          --#HELPTAG   17
          --#STATE     OPERATIONAL
          ::= 17

       nwtThresholdPhysIfOutKBytes TRAP-TYPE
          ENTERPRISE   nwTrend
          VARIABLES    {
                       nwtServerName, nwtTrapTime, nwtThreshold,
                       nwtInterval, nwtInterfaceName
                       }
          DESCRIPTION
                 "The KBytes transmitted on some interface exceeded the
                 threshold"
          --#TYPE      "Threshold - KBytes transmitted on interface"
          --#SUMMARY   "KBytes transmitted on %s exceeded "
          --#SUMMARY   "threshold of %dKB in a %d second interval "
          --#SUMMARY   "on server %s."
          --#ARGUMENTS { 4, 2, 3, 0 }
          --#SEVERITY  INFORMATIONAL
          --#TIMEINDEX 1
          --#HELP      "nwtrend.hlp"
          --#HELPTAG   18
          --#STATE     OPERATIONAL
          ::= 18

       nwtThresholdQueueNumReadyJobs TRAP-TYPE
          ENTERPRISE   nwTrend
          VARIABLES    {
                       nwtServerName, nwtTrapTime, nwtThreshold,
                       nwtQueueName, nwtInterval
                       }
          DESCRIPTION
                 "The number of ready jobs in some queue exceeded the
                 threshold"
          --#TYPE      "Threshold - queue ready jobs"
          --#SUMMARY   "Avg.# ready jobs in queue %s exceeded "
          --#SUMMARY   "threshold of %d for a %d second interval "
          --#SUMMARY   "on server %s."
          --#ARGUMENTS { 3, 2, 4, 0 }
          --#SEVERITY  INFORMATIONAL
          --#TIMEINDEX 1
          --#HELP      "nwtrend.hlp"
          --#HELPTAG   19
          --#STATE     OPERATIONAL
          ::= 19

       nwtThresholdQueueNumReadyKBytes TRAP-TYPE
          ENTERPRISE   nwTrend
          VARIABLES    {
                       nwtServerName, nwtTrapTime, nwtThreshold,
                       nwtQueueName, nwtInterval
                       }
          DESCRIPTION
                 "The number of KBytes in ready jobs in some queue
                 exceeded the threshold"
          --#TYPE      "Threshold - queue ready jobs (KB)"
          --#SUMMARY   "Avg KBytes in ready jobs in queue %s exceeded"
          --#SUMMARY   "threshold of %d for a %d second interval "
          --#SUMMARY   "on server %s."
          --#ARGUMENTS { 3, 2, 4, 0 }
          --#SEVERITY  INFORMATIONAL
          --#TIMEINDEX 1
          --#HELP      "nwtrend.hlp"
          --#HELPTAG   20
          --#STATE     OPERATIONAL
          ::= 20

       nwtThresholdQueueNextJobWaitTime TRAP-TYPE
          ENTERPRISE   nwTrend
          VARIABLES    {
                       nwtServerName, nwtTrapTime, nwtThreshold,
                       nwtQueueName
                       }
          DESCRIPTION
                 "The wait time of the next ready to run job in some
                 queue exceeded the threshold"
          --#TYPE      "Threshold - wait time of next ready job"
          --#SUMMARY   "Wait time of next ready job in queue %s "
          --#SUMMARY   "exceeded threshold of %d seconds on "
          --#SUMMARY   "server %s."
          --#ARGUMENTS { 3, 2, 0 }
          --#SEVERITY  MINOR
          --#TIMEINDEX 1
          --#HELP      "nwtrend.hlp"
          --#HELPTAG   21
          --#STATE     OPERATIONAL
          ::= 21

       nwtThresholdVolumePctFreeSpace TRAP-TYPE
          ENTERPRISE   nwTrend
          VARIABLES    {
                       nwtServerName, nwtTrapTime, nwtThreshold,
                       nwtVolumeName
                       }
          DESCRIPTION
                 "Free space on some volume fell below the threshold"
          --#TYPE      "Threshold - volume free space"
          --#SUMMARY   "Free space on volume %s fell below "
          --#SUMMARY   "threshold of %d%% on server %s."
          --#ARGUMENTS { 3, 2, 0 }
          --#SEVERITY  MINOR
          --#TIMEINDEX 1
          --#HELP      "nwtrend.hlp"
          --#HELPTAG   22
          --#STATE     OPERATIONAL
          ::= 22

       nwtThresholdPctCacheHitRate TRAP-TYPE
          ENTERPRISE   nwTrend
          VARIABLES    {
                       nwtServerName, nwtTrapTime, nwtThreshold,
                       nwtInterval
                       }
          DESCRIPTION
                 "File cache hit rate fell below the threshold"
          --#TYPE      "Threshold - file cache hit rate"
          --#SUMMARY   "File cache hit rate fell below "
          --#SUMMARY   "threshold of %d for a %d second interval "
          --#SUMMARY   "on server %s."
          --#ARGUMENTS { 2, 3, 0 }
          --#SEVERITY  MINOR
          --#TIMEINDEX 1
          --#HELP      "nwtrend.hlp"
          --#HELPTAG   23
          --#STATE     OPERATIONAL
          ::= 23

       nwtThresholdDiskPctFreeRedirectionArea TRAP-TYPE
          ENTERPRISE   nwTrend
          VARIABLES    {
                       nwtServerName, nwtTrapTime, nwtThreshold,
                       nwtDiskName
                       }
          DESCRIPTION
                 "Free redirection area on some disk fell below the
                 threshold"
          --#TYPE      "Threshold - disk free redirection area"
          --#SUMMARY   "Free redirection area on disk %s fell "
          --#SUMMARY   "below threshold of %d%% on server %s."
          --#ARGUMENTS { 3, 2, 0 }
          --#SEVERITY  CRITICAL
          --#TIMEINDEX 1
          --#HELP      "nwtrend.hlp"
          --#HELPTAG   24
          --#STATE     OPERATIONAL
          ::= 24

          END
