WINDOWS-NT-PERFORMANCE-EXCHANGE DEFINITIONS ::= BEGIN
    IMPORTS
        enterprises
            FROM RFC1155-SMI
        OBJECT-TYPE
            FROM RFC-1212
        DisplayString
            FROM RFC1213-MIB;

    microsoft   OBJECT IDENTIFIER ::= { enterprises 311 }
    software    OBJECT IDENTIFIER ::= { microsoft 1 }
    systems     OBJECT IDENTIFIER ::= { software 1 }
    os          OBJECT IDENTIFIER ::= { systems 3 }
    winnt       OBJECT IDENTIFIER ::= { os 1 }
    performance OBJECT IDENTIFIER ::= { winnt 1 }



    -- mSExchangeMTA MIB

    mSExchangeMTA OBJECT IDENTIFIER ::= { performance 1 }

    mtaAdjacentMTAAssociations OBJECT-TYPE
        SYNTAX INTEGER
        ACCESS read-only
        STATUS mandatory
        DESCRIPTION
            "Adjacent MTA Associations is the number of open associations this MTA has to other MTAs."
        ::= { mSExchangeMTA 1 }

    mtaMessagesPerSec OBJECT-TYPE
        SYNTAX Counter
        ACCESS read-only
        STATUS mandatory
        DESCRIPTION
            "Messages/sec is the rate that messages are processed."
        ::= { mSExchangeMTA 2 }

    mtaMessageBytesPerSec OBJECT-TYPE
        SYNTAX Counter
        ACCESS read-only
        STATUS mandatory
        DESCRIPTION
            "Message Bytes/sec is the rate that message bytes are processed."
        ::= { mSExchangeMTA 3 }

    mtaFreeElements OBJECT-TYPE
        SYNTAX INTEGER
        ACCESS read-only
        STATUS mandatory
        DESCRIPTION
            "Free Elements is the number of free buffer elements in the MTA pool."
        ::= { mSExchangeMTA 4 }

    mtaFreeHeaders OBJECT-TYPE
        SYNTAX INTEGER
        ACCESS read-only
        STATUS mandatory
        DESCRIPTION
            "Free Headers is the number of free buffer headers in the MTA pool."
        ::= { mSExchangeMTA 5 }

    mtaAdminConnections OBJECT-TYPE
        SYNTAX INTEGER
        ACCESS read-only
        STATUS mandatory
        DESCRIPTION
            "Admin Connections is the number of Microsoft Exchange Administrator programs connected to this MTA."
        ::= { mSExchangeMTA 6 }

    mtaThreadsInUse OBJECT-TYPE
        SYNTAX INTEGER
        ACCESS read-only
        STATUS mandatory
        DESCRIPTION
            "Threads in Use is the number of threads in use by the MTA (does not include RPC threads). This number can be used to determine whether additional processors could be of benefit."
        ::= { mSExchangeMTA 7 }

    mtaWorkQueueLength OBJECT-TYPE
        SYNTAX INTEGER
        ACCESS read-only
        STATUS mandatory
        DESCRIPTION
            "Work Queue Length is the number of outstanding messages in the Work Queue, which indicates the number of messages not yet processed to completion by the MTA."
        ::= { mSExchangeMTA 8 }

    mtaXAPIGateways OBJECT-TYPE
        SYNTAX INTEGER
        ACCESS read-only
        STATUS mandatory
        DESCRIPTION
            "XAPI Gateways is the number of gateways connected to the MTA using the XAPI MT/OM interface. A single gateway may have multiple XAPI gateway sessions."
        ::= { mSExchangeMTA 9 }

    mtaXAPIClients OBJECT-TYPE
        SYNTAX INTEGER
        ACCESS read-only
        STATUS mandatory
        DESCRIPTION
            "XAPI Clients is the number of XAPI clients connected to the MTA using the XAPI MA/OM interface. A single client may have multiple XAPI client sessions."
        ::= { mSExchangeMTA 10 }

    mtaDiskFileDeletesPerSec OBJECT-TYPE
        SYNTAX Counter
        ACCESS read-only
        STATUS mandatory
        DESCRIPTION
            "Disk File Deletes/sec is the rate of disk file delete operations."
        ::= { mSExchangeMTA 11 }

    mtaDiskFileSyncsPerSec OBJECT-TYPE
        SYNTAX Counter
        ACCESS read-only
        STATUS mandatory
        DESCRIPTION
            "Disk File Syncs/sec is the rate of disk file sync operations."
        ::= { mSExchangeMTA 12 }

    mtaDiskFileOpensPerSec OBJECT-TYPE
        SYNTAX Counter
        ACCESS read-only
        STATUS mandatory
        DESCRIPTION
            "Disk File Opens/sec is the rate of disk file open operations."
        ::= { mSExchangeMTA 13 }

    mtaDiskFileReadsPerSec OBJECT-TYPE
        SYNTAX Counter
        ACCESS read-only
        STATUS mandatory
        DESCRIPTION
            "Disk File Reads/sec is the rate of disk file read operations."
        ::= { mSExchangeMTA 14 }

    mtaDiskFileWritesPerSec OBJECT-TYPE
        SYNTAX Counter
        ACCESS read-only
        STATUS mandatory
        DESCRIPTION
            "Disk File Writes/sec is the rate of disk file write operations."
        ::= { mSExchangeMTA 15 }

    mtaExDSReadCallsPerSec OBJECT-TYPE
        SYNTAX Counter
        ACCESS read-only
        STATUS mandatory
        DESCRIPTION
            "ExDS Read Calls/sec is the rate of read calls to the directory service."
        ::= { mSExchangeMTA 16 }

    mtaXAPIReceiveBytesPerSec OBJECT-TYPE
        SYNTAX Counter
        ACCESS read-only
        STATUS mandatory
        DESCRIPTION
            "XAPI Receive Bytes/sec is the rate that bytes are received over a XAPI connection."
        ::= { mSExchangeMTA 17 }

    mtaXAPITransmitBytesPerSec OBJECT-TYPE
        SYNTAX Counter
        ACCESS read-only
        STATUS mandatory
        DESCRIPTION
            "XAPI Transmit Bytes/sec is the rate that bytes are transmitted over a XAPI connection."
        ::= { mSExchangeMTA 18 }

    mtaAdminInterfaceReceiveBytesPerSec OBJECT-TYPE
        SYNTAX Counter
        ACCESS read-only
        STATUS mandatory
        DESCRIPTION
            "Admin Interface Receive Bytes/sec is the rate that bytes are received over an Admin connection."
        ::= { mSExchangeMTA 19 }

    mtaAdminInterfaceTransmitBytesPerSec OBJECT-TYPE
        SYNTAX Counter
        ACCESS read-only
        STATUS mandatory
        DESCRIPTION
            "Admin Interface Transmit Bytes/sec is the rate that bytes are transmitted over an Admin connection."
        ::= { mSExchangeMTA 20 }

    mtaLANReceiveBytesPerSec OBJECT-TYPE
        SYNTAX Counter
        ACCESS read-only
        STATUS mandatory
        DESCRIPTION
            "LAN Receive Bytes/sec is the rate that bytes are received over a LAN from MTAs."
        ::= { mSExchangeMTA 21 }

    mtaLANTransmitBytesPerSec OBJECT-TYPE
        SYNTAX Counter
        ACCESS read-only
        STATUS mandatory
        DESCRIPTION
            "LAN Transmit Bytes/sec is the rate that bytes are transmitted over a LAN to MTAs."
        ::= { mSExchangeMTA 22 }

    mtaRASReceiveBytesPerSec OBJECT-TYPE
        SYNTAX Counter
        ACCESS read-only
        STATUS mandatory
        DESCRIPTION
            "RAS Receive Bytes/sec is the rate that bytes are received over a RAS connection."
        ::= { mSExchangeMTA 23 }

    mtaRASTransmitBytesPerSec OBJECT-TYPE
        SYNTAX Counter
        ACCESS read-only
        STATUS mandatory
        DESCRIPTION
            "RAS Transmit Bytes/sec is the rate that bytes are transmitted over a RAS connection."
        ::= { mSExchangeMTA 24 }

    mtaTCPPerIPReceiveBytesPerSec OBJECT-TYPE
        SYNTAX Counter
        ACCESS read-only
        STATUS mandatory
        DESCRIPTION
            "TCP/IP Receive Bytes/sec is the rate that bytes are received over a TCP/IP connection."
        ::= { mSExchangeMTA 25 }

    mtaTCPPerIPTransmitBytesPerSec OBJECT-TYPE
        SYNTAX Counter
        ACCESS read-only
        STATUS mandatory
        DESCRIPTION
            "TCP/IP Transmit Bytes/sec is the rate that bytes are transmitted over a TCP/IP connection."
        ::= { mSExchangeMTA 26 }

    mtaTP4ReceiveBytesPerSec OBJECT-TYPE
        SYNTAX Counter
        ACCESS read-only
        STATUS mandatory
        DESCRIPTION
            "TP4 Receive Bytes/sec is the rate that bytes are received over a TP4 connection."
        ::= { mSExchangeMTA 27 }

    mtaTP4TransmitBytesPerSec OBJECT-TYPE
        SYNTAX Counter
        ACCESS read-only
        STATUS mandatory
        DESCRIPTION
            "TP4 Transmit Bytes/sec is the rate that bytes are transmitted over a TP4 connection."
        ::= { mSExchangeMTA 28 }

    mtaX25ReceiveBytesPerSec OBJECT-TYPE
        SYNTAX Counter
        ACCESS read-only
        STATUS mandatory
        DESCRIPTION
            "X.25 Receive Bytes/sec is the rate that bytes are received over an X.25 connection."
        ::= { mSExchangeMTA 29 }

    mtaX25TransmitBytesPerSec OBJECT-TYPE
        SYNTAX Counter
        ACCESS read-only
        STATUS mandatory
        DESCRIPTION
            "X.25 Transmit Bytes/sec is the rate that bytes are transmitted over an X.25 connection."
        ::= { mSExchangeMTA 30 }

    mtaDeferredDeliveryMsgs OBJECT-TYPE
        SYNTAX INTEGER
        ACCESS read-only
        STATUS mandatory
        DESCRIPTION
            "Deferred Delivery Msgs is the total number of deferred delivery messages currently stored in the MTA."
        ::= { mSExchangeMTA 31 }

    mtaTotalRecipientsQueued OBJECT-TYPE
        SYNTAX INTEGER
        ACCESS read-only
        STATUS mandatory
        DESCRIPTION
            "Total Recipients Queued is the total number of recipients specified in all messages currently stored in the MTA."
        ::= { mSExchangeMTA 32 }

    mtaTotalSuccessfulConversions OBJECT-TYPE
        SYNTAX INTEGER
        ACCESS read-only
        STATUS mandatory
        DESCRIPTION
            "Total Successful Conversions is the total number of messages successfully converted from one form to another since MTA initialization."
        ::= { mSExchangeMTA 33 }

    mtaTotalFailedConversions OBJECT-TYPE
        SYNTAX INTEGER
        ACCESS read-only
        STATUS mandatory
        DESCRIPTION
            "Total Failed Conversions is the total number of messages which failed to be converted from one form to another since MTA initialization."
        ::= { mSExchangeMTA 34 }

    mtaTotalLoopsDetected OBJECT-TYPE
        SYNTAX INTEGER
        ACCESS read-only
        STATUS mandatory
        DESCRIPTION
            "Total Loops Detected is the total number  of messages detected to have looped since MTA initialization."
        ::= { mSExchangeMTA 35 }

    mtaInboundMessagesTotal OBJECT-TYPE
        SYNTAX Counter
        ACCESS read-only
        STATUS mandatory
        DESCRIPTION
            "Inbound Messages Total is the total number of messages received since MTA initialization."
        ::= { mSExchangeMTA 36 }

    mtaOutboundMessagesTotal OBJECT-TYPE
        SYNTAX Counter
        ACCESS read-only
        STATUS mandatory
        DESCRIPTION
            "Outbound Messages Total is the total number of messages transmitted since MTA initialization."
        ::= { mSExchangeMTA 37 }

    mtaInboundBytesTotal OBJECT-TYPE
        SYNTAX Counter
        ACCESS read-only
        STATUS mandatory
        DESCRIPTION
            "Inbound Bytes Total is the total volume of message content received since MTA initialization, measured in kilobytes."
        ::= { mSExchangeMTA 38 }

    mtaWorkQueueBytes OBJECT-TYPE
        SYNTAX Counter
        ACCESS read-only
        STATUS mandatory
        DESCRIPTION
            "Work Queue Bytes is the total volume of message content currently stored in the MTA, measured in kilobytes."
        ::= { mSExchangeMTA 39 }

    mtaOutboundBytesTotal OBJECT-TYPE
        SYNTAX Counter
        ACCESS read-only
        STATUS mandatory
        DESCRIPTION
            "Outbound Bytes Total is the total volume of message content transmitted since MTA initialization, measured in kilobytes."
        ::= { mSExchangeMTA 40 }

    mtaTotalRecipientsInbound OBJECT-TYPE
        SYNTAX Counter
        ACCESS read-only
        STATUS mandatory
        DESCRIPTION
            "Total Recipients Inbound is the total number of recipients specified in all messages received since MTA initialization."
        ::= { mSExchangeMTA 41 }

    mtaTotalRecipientsOutbound OBJECT-TYPE
        SYNTAX Counter
        ACCESS read-only
        STATUS mandatory
        DESCRIPTION
            "Total Recipients Outbound is the total number of recipients specified in all messages transmitted since MTA initialization."
        ::= { mSExchangeMTA 42 }

    -- mSExchangeMTA Connections MIB

    connmSExchangeMTA-ConnectionsTable OBJECT-TYPE
        SYNTAX SEQUENCE OF connmSExchangeMTA-ConnectionsEntry
        ACCESS not-accessible
        STATUS mandatory
        DESCRIPTION
            "A table containing performance information for instances of 'mSExchangeMTA-Connections' objects."
        ::= { performance 2 }

    connmSExchangeMTA-ConnectionsEntry OBJECT-TYPE
        SYNTAX connmSExchangeMTA-ConnectionsEntry
        ACCESS not-accessible
        STATUS mandatory
        DESCRIPTION
            "Performance information for one particular instance of 'mSExchangeMTA-Connections' object."
        INDEX { connmSExchangeMTA-ConnectionsIndex }
        ::= { connmSExchangeMTA-ConnectionsTable 1 }

    connmSExchangeMTA-ConnectionsEntry ::=
        SEQUENCE {
            connmSExchangeMTA-ConnectionsIndex INTEGER,
            connmSExchangeMTA-ConnectionsInstance DisplayString,
            connAssociations INTEGER,
            connReceiveBytesPerSec Counter,
            connSendBytesPerSec Counter,
            connReceiveMessagesPerSec Counter,
            connSendMessagesPerSec Counter,
            connQueueLength INTEGER,
            connConnectorIndex INTEGER,
            connInboundRejectedTotal INTEGER,
            connTotalRecipientsQueued INTEGER,
            connOldestMessageQueued TimeTicks,
            connCurrentInboundAssociations INTEGER,
            connCurrentOutboundAssociations INTEGER,
            connCumulativeInboundAssociations INTEGER,
            connCumulativeOutboundAssociations INTEGER,
            connLastInboundAssociation TimeTicks,
            connLastOutboundAssociation TimeTicks,
            connRejectedInboundAssociations INTEGER,
            connFailedOutboundAssociations INTEGER,
            connNextAssociationRetry INTEGER,
            connInboundRejectReason INTEGER,
            connOutboundFailureReason INTEGER,
            connInboundMessagesTotal Counter,
            connOutboundMessagesTotal Counter,
            connInboundBytesTotal Counter,
            connQueuedBytes Counter,
            connOutboundBytesTotal Counter,
            connTotalRecipientsInbound Counter,
            connTotalRecipientsOutbound Counter
        }

    connmSExchangeMTA-ConnectionsIndex OBJECT-TYPE
        SYNTAX INTEGER
        ACCESS read-only
        STATUS mandatory
        DESCRIPTION
            "Index."
        ::= { connmSExchangeMTA-ConnectionsEntry 1 }

    connmSExchangeMTA-ConnectionsInstance OBJECT-TYPE
        SYNTAX DisplayString
        ACCESS read-only
        STATUS mandatory
        DESCRIPTION
            "Instance name."
        ::= { connmSExchangeMTA-ConnectionsEntry 2 }

    connAssociations OBJECT-TYPE
        SYNTAX INTEGER
        ACCESS read-only
        STATUS mandatory
        DESCRIPTION
            "Associations is the number of associations between the MTA and the connected entity. MTAs may open multiple associations if additional transfer throughput is necessary."
        ::= { connmSExchangeMTA-ConnectionsEntry 3 }

    connReceiveBytesPerSec OBJECT-TYPE
        SYNTAX Counter
        ACCESS read-only
        STATUS mandatory
        DESCRIPTION
            "Receive Bytes/sec is the rate that bytes are received from the connected entity."
        ::= { connmSExchangeMTA-ConnectionsEntry 4 }

    connSendBytesPerSec OBJECT-TYPE
        SYNTAX Counter
        ACCESS read-only
        STATUS mandatory
        DESCRIPTION
            "Send Bytes/sec is the rate that bytes are sent to the connected entity."
        ::= { connmSExchangeMTA-ConnectionsEntry 5 }

    connReceiveMessagesPerSec OBJECT-TYPE
        SYNTAX Counter
        ACCESS read-only
        STATUS mandatory
        DESCRIPTION
            "Receive Messages/sec is the rate that messages are received from the connected entity."
        ::= { connmSExchangeMTA-ConnectionsEntry 6 }

    connSendMessagesPerSec OBJECT-TYPE
        SYNTAX Counter
        ACCESS read-only
        STATUS mandatory
        DESCRIPTION
            "Send Messages/sec is the rate that messages are sent to the connected entity."
        ::= { connmSExchangeMTA-ConnectionsEntry 7 }

    connQueueLength OBJECT-TYPE
        SYNTAX INTEGER
        ACCESS read-only
        STATUS mandatory
        DESCRIPTION
            "Queue Length is the number of outstanding messages queued for transfer to the entity."
        ::= { connmSExchangeMTA-ConnectionsEntry 8 }

    connConnectorIndex OBJECT-TYPE
        SYNTAX INTEGER
        ACCESS read-only
        STATUS mandatory
        DESCRIPTION
            "Connector Index is a unique index associated with a connector entity."
        ::= { connmSExchangeMTA-ConnectionsEntry 9 }

    connInboundRejectedTotal OBJECT-TYPE
        SYNTAX INTEGER
        ACCESS read-only
        STATUS mandatory
        DESCRIPTION
            "Inbound Rejected Total is the total number of messages rejected from this entity since MTA initialization."
        ::= { connmSExchangeMTA-ConnectionsEntry 10 }

    connTotalRecipientsQueued OBJECT-TYPE
        SYNTAX INTEGER
        ACCESS read-only
        STATUS mandatory
        DESCRIPTION
            "Total Recipients Queued is the total number of recipients specified in all messages currently stored in this entity's queue."
        ::= { connmSExchangeMTA-ConnectionsEntry 11 }

    connOldestMessageQueued OBJECT-TYPE
        SYNTAX TimeTicks
        ACCESS read-only
        STATUS mandatory
        DESCRIPTION
            "Oldest Message Queued is the time (secs) since the oldest message in this entity's queue was placed in the queue."
        ::= { connmSExchangeMTA-ConnectionsEntry 12 }

    connCurrentInboundAssociations OBJECT-TYPE
        SYNTAX INTEGER
        ACCESS read-only
        STATUS mandatory
        DESCRIPTION
            "Current Inbound Associations is the current number of inbound (remote initiated) associations with the entity."
        ::= { connmSExchangeMTA-ConnectionsEntry 13 }

    connCurrentOutboundAssociations OBJECT-TYPE
        SYNTAX INTEGER
        ACCESS read-only
        STATUS mandatory
        DESCRIPTION
            "Current Outbound Associations is the current number of outbound (locally initiated) associations with the entity."
        ::= { connmSExchangeMTA-ConnectionsEntry 14 }

    connCumulativeInboundAssociations OBJECT-TYPE
        SYNTAX INTEGER
        ACCESS read-only
        STATUS mandatory
        DESCRIPTION
            "Cumulative Inbound Associations is the total number of inbound (remote initiated) associations with the entity, since MTA initialization."
        ::= { connmSExchangeMTA-ConnectionsEntry 15 }

    connCumulativeOutboundAssociations OBJECT-TYPE
        SYNTAX INTEGER
        ACCESS read-only
        STATUS mandatory
        DESCRIPTION
            "Cumulative Outbound Associations is the total number of outbound (locally initiated) associations with the entity, since MTA initialization."
        ::= { connmSExchangeMTA-ConnectionsEntry 16 }

    connLastInboundAssociation OBJECT-TYPE
        SYNTAX TimeTicks
        ACCESS read-only
        STATUS mandatory
        DESCRIPTION
            "Last Inbound Association is the time (secs) since the last time an inbound (remote initiated) association for this entity was active."
        ::= { connmSExchangeMTA-ConnectionsEntry 17 }

    connLastOutboundAssociation OBJECT-TYPE
        SYNTAX TimeTicks
        ACCESS read-only
        STATUS mandatory
        DESCRIPTION
            "Last Outbound Association is the time (secs) since the last time an outbound (locally initiated) association for this entity was active."
        ::= { connmSExchangeMTA-ConnectionsEntry 18 }

    connRejectedInboundAssociations OBJECT-TYPE
        SYNTAX INTEGER
        ACCESS read-only
        STATUS mandatory
        DESCRIPTION
            "Rejected Inbound Associations is the total number of inbound (remote initiated) associations that have been rejected, since MTA initialization."
        ::= { connmSExchangeMTA-ConnectionsEntry 19 }

    connFailedOutboundAssociations OBJECT-TYPE
        SYNTAX INTEGER
        ACCESS read-only
        STATUS mandatory
        DESCRIPTION
            "Failed Outbound Associations is the total number of outbound (locally initiated) associations that have failed, since MTA initialization."
        ::= { connmSExchangeMTA-ConnectionsEntry 20 }

    connNextAssociationRetry OBJECT-TYPE
        SYNTAX INTEGER
        ACCESS read-only
        STATUS mandatory
        DESCRIPTION
            "Next Association Retry is the time (secs since 00:00 1st Jan 1970) when this entity is next scheduled to attempt to open an association."
        ::= { connmSExchangeMTA-ConnectionsEntry 21 }

    connInboundRejectReason OBJECT-TYPE
        SYNTAX INTEGER
        ACCESS read-only
        STATUS mandatory
        DESCRIPTION
            "Inbound Reject Reason is the reject reason code, if any, for the last association rejected from this entity."
        ::= { connmSExchangeMTA-ConnectionsEntry 22 }

    connOutboundFailureReason OBJECT-TYPE
        SYNTAX INTEGER
        ACCESS read-only
        STATUS mandatory
        DESCRIPTION
            "Outbound Failure Reason is the failure reason code, if any, for the last association attempt to this entity."
        ::= { connmSExchangeMTA-ConnectionsEntry 23 }

    connInboundMessagesTotal OBJECT-TYPE
        SYNTAX Counter
        ACCESS read-only
        STATUS mandatory
        DESCRIPTION
            "Inbound Messages Total is the total number of messages received from this entity since MTA initialization."
        ::= { connmSExchangeMTA-ConnectionsEntry 24 }

    connOutboundMessagesTotal OBJECT-TYPE
        SYNTAX Counter
        ACCESS read-only
        STATUS mandatory
        DESCRIPTION
            "Outbound Messages Total is the total number of messages transmitted to this entity since MTA initialization."
        ::= { connmSExchangeMTA-ConnectionsEntry 25 }

    connInboundBytesTotal OBJECT-TYPE
        SYNTAX Counter
        ACCESS read-only
        STATUS mandatory
        DESCRIPTION
            "Inbound Bytes Total is the total volume of message content received from this entity since MTA initialization, measured in kilobytes."
        ::= { connmSExchangeMTA-ConnectionsEntry 26 }

    connQueuedBytes OBJECT-TYPE
        SYNTAX Counter
        ACCESS read-only
        STATUS mandatory
        DESCRIPTION
            "Queued Bytes is the total volume of message content currently stored in this entity's queue, measured in kilobytes."
        ::= { connmSExchangeMTA-ConnectionsEntry 27 }

    connOutboundBytesTotal OBJECT-TYPE
        SYNTAX Counter
        ACCESS read-only
        STATUS mandatory
        DESCRIPTION
            "Outbound Bytes Total is the total volume of message content transmitted to this entity since MTA initialization, measured in kilobytes."
        ::= { connmSExchangeMTA-ConnectionsEntry 28 }

    connTotalRecipientsInbound OBJECT-TYPE
        SYNTAX Counter
        ACCESS read-only
        STATUS mandatory
        DESCRIPTION
            "Total Recipients Inbound is the total number of recipients specified in all messages received from this entity since MTA initialization."
        ::= { connmSExchangeMTA-ConnectionsEntry 29 }

    connTotalRecipientsOutbound OBJECT-TYPE
        SYNTAX Counter
        ACCESS read-only
        STATUS mandatory
        DESCRIPTION
            "Total Recipients Outbound is the total number of recipients specified in all messages transmitted to this entity since MTA initialization."
        ::= { connmSExchangeMTA-ConnectionsEntry 30 }

    -- mSExchangeIMC MIB

    mSExchangeIMC OBJECT IDENTIFIER ::= { performance 3 }

    imsQueuedMTS-IN OBJECT-TYPE
        SYNTAX INTEGER
        ACCESS read-only
        STATUS mandatory
        DESCRIPTION
            "The number of messages awaiting final delivery in MS Exchange Server"
        ::= { mSExchangeIMC 1 }

    imsBytesQueuedMTS-IN OBJECT-TYPE
        SYNTAX INTEGER
        ACCESS read-only
        STATUS mandatory
        DESCRIPTION
            "The size, in bytes, of the messages that have been converted from Internet Mail and are awaiting final delivery within MS Exchange Server"
        ::= { mSExchangeIMC 2 }

    imsMessagesEnteringMTS-IN OBJECT-TYPE
        SYNTAX INTEGER
        ACCESS read-only
        STATUS mandatory
        DESCRIPTION
            "The number of messages entering the MTS-IN folder after conversion from Internet Mail format per hour"
        ::= { mSExchangeIMC 3 }

    imsQueuedMTS-OUT OBJECT-TYPE
        SYNTAX INTEGER
        ACCESS read-only
        STATUS mandatory
        DESCRIPTION
            "The number of messages waiting to be converted to Internet Mail format"
        ::= { mSExchangeIMC 4 }

    imsBytesQueuedMTS-OUT OBJECT-TYPE
        SYNTAX INTEGER
        ACCESS read-only
        STATUS mandatory
        DESCRIPTION
            "The size, in bytes, of the messages waiting to be converted to Internet Mail format"
        ::= { mSExchangeIMC 5 }

    imsMessagesEnteringMTS-OUT OBJECT-TYPE
        SYNTAX INTEGER
        ACCESS read-only
        STATUS mandatory
        DESCRIPTION
            "Messages that have entered the Internet Mail Service"
        ::= { mSExchangeIMC 6 }

    imsMessagesLeavingMTS-OUT OBJECT-TYPE
        SYNTAX INTEGER
        ACCESS read-only
        STATUS mandatory
        DESCRIPTION
            "The number of messages entering the Outbound Queue per hour"
        ::= { mSExchangeIMC 7 }

    imsConnectionsInbound OBJECT-TYPE
        SYNTAX INTEGER
        ACCESS read-only
        STATUS mandatory
        DESCRIPTION
            "The number of current SMTP connections to the Internet Mail Service established by other SMTP hosts"
        ::= { mSExchangeIMC 8 }

    imsConnectionsOutbound OBJECT-TYPE
        SYNTAX INTEGER
        ACCESS read-only
        STATUS mandatory
        DESCRIPTION
            "The number of current SMTP connections the Internet Mail Service has established to other SMTP hosts"
        ::= { mSExchangeIMC 9 }

    imsConnectionsTotalOutbound OBJECT-TYPE
        SYNTAX INTEGER
        ACCESS read-only
        STATUS mandatory
        DESCRIPTION
            "The total number of successful SMTP connections that the Internet Mail Service has established since it was started"
        ::= { mSExchangeIMC 10 }

    imsConnectionsTotalInbound OBJECT-TYPE
        SYNTAX INTEGER
        ACCESS read-only
        STATUS mandatory
        DESCRIPTION
            "The total number of SMTP connections the Internet Mail Service has accepted from other hosts since it was started"
        ::= { mSExchangeIMC 11 }

    imsConnectionsTotalRejected OBJECT-TYPE
        SYNTAX INTEGER
        ACCESS read-only
        STATUS mandatory
        DESCRIPTION
            "The total number of SMTP connections that the Internet Mail Service has rejected from other hosts since it was started"
        ::= { mSExchangeIMC 12 }

    imsConnectionsTotalFailed OBJECT-TYPE
        SYNTAX INTEGER
        ACCESS read-only
        STATUS mandatory
        DESCRIPTION
            "The total number of SMTP connections the Internet Mail Service has attempted to other hosts that failed since it was started"
        ::= { mSExchangeIMC 13 }

    imsQueuedOutbound OBJECT-TYPE
        SYNTAX INTEGER
        ACCESS read-only
        STATUS mandatory
        DESCRIPTION
            "The number of messages from MS Exchange Server, that are queued to be delivered to the Internet"
        ::= { mSExchangeIMC 14 }

    imsQueuedInbound OBJECT-TYPE
        SYNTAX INTEGER
        ACCESS read-only
        STATUS mandatory
        DESCRIPTION
            "The number of messages received from the Internet destined for MS Exchange Server"
        ::= { mSExchangeIMC 15 }

    imsNDRsTotalInbound OBJECT-TYPE
        SYNTAX INTEGER
        ACCESS read-only
        STATUS mandatory
        DESCRIPTION
            "The total number of Non-delivery reports generated for outbound mail"
        ::= { mSExchangeIMC 16 }

    imsNDRsTotalOutbound OBJECT-TYPE
        SYNTAX INTEGER
        ACCESS read-only
        STATUS mandatory
        DESCRIPTION
            "The total number of Non-delivery reports generated for inbound mail"
        ::= { mSExchangeIMC 17 }

    imsTotalInboundKilobytes OBJECT-TYPE
        SYNTAX INTEGER
        ACCESS read-only
        STATUS mandatory
        DESCRIPTION
            "The total kilobytes of message data transferred into the MS Exchange Server"
        ::= { mSExchangeIMC 18 }

    imsTotalOutboundKilobytes OBJECT-TYPE
        SYNTAX INTEGER
        ACCESS read-only
        STATUS mandatory
        DESCRIPTION
            "The total kilobytes of message data transferred out of the MS Exchange Server"
        ::= { mSExchangeIMC 19 }

    imsInboundMessagesTotal OBJECT-TYPE
        SYNTAX INTEGER
        ACCESS read-only
        STATUS mandatory
        DESCRIPTION
            "The total number of Internet messages delivered into MS Exchange Server"
        ::= { mSExchangeIMC 20 }

    imsOutboundMessagesTotal OBJECT-TYPE
        SYNTAX INTEGER
        ACCESS read-only
        STATUS mandatory
        DESCRIPTION
            "The total number of outbound messages delivered to their destinations"
        ::= { mSExchangeIMC 21 }

    imsInboundBytesPerHr OBJECT-TYPE
        SYNTAX INTEGER
        ACCESS read-only
        STATUS mandatory
        DESCRIPTION
            "The hourly rate of bytes transferred to the MS Exchange Server"
        ::= { mSExchangeIMC 22 }

    imsOutboundBytesPerHr OBJECT-TYPE
        SYNTAX INTEGER
        ACCESS read-only
        STATUS mandatory
        DESCRIPTION
            "The hourly rate of bytes transferred to the Internet"
        ::= { mSExchangeIMC 23 }

    imsInboundMessagesPerHr OBJECT-TYPE
        SYNTAX INTEGER
        ACCESS read-only
        STATUS mandatory
        DESCRIPTION
            "The hourly rate messages are transferred to the MS Exchange server"
        ::= { mSExchangeIMC 24 }

    imsOutboundMessagesPerHr OBJECT-TYPE
        SYNTAX INTEGER
        ACCESS read-only
        STATUS mandatory
        DESCRIPTION
            "The hourly rate messages are transferred to the Internet"
        ::= { mSExchangeIMC 25 }

    imsOutboundConnectionsPerHr OBJECT-TYPE
        SYNTAX INTEGER
        ACCESS read-only
        STATUS mandatory
        DESCRIPTION
            "The hourly rate at which outbound connections were made"
        ::= { mSExchangeIMC 26 }

    imsInboundConnectionsPerHr OBJECT-TYPE
        SYNTAX INTEGER
        ACCESS read-only
        STATUS mandatory
        DESCRIPTION
            "The hourly rate at which inbound connections were received"
        ::= { mSExchangeIMC 27 }

    imsTotalMessagesQueued OBJECT-TYPE
        SYNTAX INTEGER
        ACCESS read-only
        STATUS mandatory
        DESCRIPTION
            "Total messages waiting in the Internet Mail Service queues"
        ::= { mSExchangeIMC 28 }

    imsTotalKilobytesQueued OBJECT-TYPE
        SYNTAX INTEGER
        ACCESS read-only
        STATUS mandatory
        DESCRIPTION
            "Total kilobytes of message data queued in the Internet Mail Service queues"
        ::= { mSExchangeIMC 29 }

    imsTotalInboundRecipients OBJECT-TYPE
        SYNTAX INTEGER
        ACCESS read-only
        STATUS mandatory
        DESCRIPTION
            "Total number of recipients processed inbound since the Internet Mail Service was started"
        ::= { mSExchangeIMC 30 }

    imsTotalOutboundRecipients OBJECT-TYPE
        SYNTAX INTEGER
        ACCESS read-only
        STATUS mandatory
        DESCRIPTION
            "Total number of recipients processed outbound since the Internet Mail Service was started"
        ::= { mSExchangeIMC 31 }

    imsTotalRecipientsQueued OBJECT-TYPE
        SYNTAX INTEGER
        ACCESS read-only
        STATUS mandatory
        DESCRIPTION
            "Total number of recipients in the Internet Mail Service queues"
        ::= { mSExchangeIMC 32 }

    imsTotalSuccessfulConversions OBJECT-TYPE
        SYNTAX INTEGER
        ACCESS read-only
        STATUS mandatory
        DESCRIPTION
            "Total message format conversions between internet format and Exchange format that succeeded."
        ::= { mSExchangeIMC 33 }

    imsTotalFailedConversions OBJECT-TYPE
        SYNTAX INTEGER
        ACCESS read-only
        STATUS mandatory
        DESCRIPTION
            "Total message format conversions between internet format and Exchange format that failed."
        ::= { mSExchangeIMC 34 }

    imsTotalLoopsDetected OBJECT-TYPE
        SYNTAX INTEGER
        ACCESS read-only
        STATUS mandatory
        DESCRIPTION
            "Total number of messages NDRd because they appeared to be looping infinitely."
        ::= { mSExchangeIMC 35 }

    END
