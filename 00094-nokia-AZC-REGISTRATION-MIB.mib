NOKIA-AZC-REGISTRATION-MIB DEFINITIONS ::= BEGIN

-- 4567890123456789012345678901234567890123456789012345678901234567890123456789
-- This line is 80 characters wide, keep lines in this file shorter than that--
-- ===============================================================
--	   Copyright (C) Nokia Corporation 1999
-- ===============================================================
-- This MIB Module defines the System MIB for products running AZC (P020).
-- More detailed description of the variables and tables is
-- provided in other related documentation.
--
-- Format:   SNMP v2 MIB (Simple network management protocol,
--	     version 2, Management Information Base  )
--
-- ================================================================
-- Author      : Raimo Vuonnala
-- Version     : 1.1
-- Created     : 01.10.1999
-- Last Update : 13.10.1999
-- ================================================================

IMPORTS

    enterprises
	    FROM RFC1155-SMI;

nokia			OBJECT IDENTIFIER ::= { enterprises 94 }
nokiaProducts		OBJECT IDENTIFIER ::= { nokia 1 }
azcProducts		OBJECT IDENTIFIER ::= { nokiaProducts 32 }
azcProductIds		OBJECT IDENTIFIER ::= { azcProducts 1 }

Unknown			OBJECT IDENTIFIER ::= { azcProductIds 1 }
P020                    OBJECT IDENTIFIER ::= { azcProductIds 2 }


END
