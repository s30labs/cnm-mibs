DX-TRAP-MIB DEFINITIONS ::= BEGIN

-- Title:	DX-TRAP-MIB 
-- Date:	April 4, 2003
-- By:		Yogendra Singh <yogi@juniper.net>
--
-- Copyright 2003-2005 Redline Networks, Inc. All rights reserved.
-- Copyright 2005 Juniper Networks, Inc. All rights reserved.

IMPORTS MODULE-IDENTITY, OBJECT-TYPE,enterprises, IpAddress 
                FROM SNMPv2-SMI
        DisplayString 
                FROM SNMPv2-TC
        juniperDX, dx,
                FROM DX-MIB;

--IMPORTS
--         enterprises
--                  FROM RFC1155-SMI
--         OBJECT-TYPE
--                  FROM RFC-1212
--         DisplayString
--                  FROM RFC1213-MIB;
-- $Rl: DX-TRAP-MIB.txt,v 1.4.22.1 2007/10/20 17:33:05 atul Exp $`
--
-- Note: this MIB is Read-Only.
--

---------------------------------------------------------------------------
-- All the DX  enterprise trap mib definitions. 
---------------------------------------------------------------------------
dxTraps OBJECT IDENTIFIER ::= { dx 5 }


vipStateUp TRAP-TYPE
    ENTERPRISE     dxTraps
    DESCRIPTION
                "This trap indicates that the current VIP  state is up."
        ::= 1

vipStateDown TRAP-TYPE
    ENTERPRISE     dxTraps
    DESCRIPTION
                "This trap indicates that the current VIP state is down."
        ::= 2

targetServerStateUp TRAP-TYPE
    ENTERPRISE     dxTraps
    DESCRIPTION
                "This trap indicates that the current target server state is up."
        ::= 3

targetServerStateDown TRAP-TYPE
    ENTERPRISE     dxTraps
    DESCRIPTION
                "This trap indicates that the current target server state is down."
        ::= 4

failoverStateActive TRAP-TYPE
    ENTERPRISE     dxTraps
    DESCRIPTION
                "This trap indicates that the DX is running in Active mode."
        ::= 5

userAutheniticationFailure TRAP-TYPE
    ENTERPRISE     dxTraps
    DESCRIPTION
                "This trap is generated when the user login failure threshold limit
                is reached."
         ::= 6

connectionThresholdTrap TRAP-TYPE
    ENTERPRISE     dxTraps
    DESCRIPTION
                "This trap indicates that user defined maximum connection threshold limit
                         is reached."
        ::= 7

failoverDueToHealth TRAP-TYPE
    ENTERPRISE     dxTraps
    DESCRIPTION
                "This trap indicates that the DX is failing over
                 due to a remotehost healthcheck failure."
        ::= 9

failoverStateStandby TRAP-TYPE
	ENTERPRISE     dxTraps
	DESCRIPTION
		        "This trap indicates that the DX is running in Standby mode."
        ::= 10

failoverStateMaster TRAP-TYPE
	ENTERPRISE     dxTraps
	DESCRIPTION
		        "This trap indicates that the DX is running in Master mode."
        ::= 11

failoverStateIdle TRAP-TYPE
	ENTERPRISE     dxTraps
	DESCRIPTION
		        "This trap indicates that the DX is running in Idle mode."
        ::= 12

END
