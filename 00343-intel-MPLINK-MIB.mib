INTEL-MPLINK-MIB DEFINITIONS ::= BEGIN

-- Copyright (C) 1997 Intel Corporation. All rights reserved.
--
-- MP Link 2 MIB, $Date: 1999/07/07 10:21:45 $
--
-- Defines objects for proprietary multi protocol links.
--
-- Build 2
--

IMPORTS
    Counter                             FROM RFC1155-SMI
    DisplayString                       FROM RFC1213-MIB
    mib2ext                             FROM INTEL-GEN-MIB
    OBJECT-TYPE                         FROM RFC-1212;


OnOff ::= INTEGER { on(1), off(2) }
Attachment ::= INTEGER { none(1), tenbase-t(2), aui(3),
    id0(4), id1(5), id2(6), id3(7),
    eia530-dce(8), test-plug(9),
    v11-dce(10), v24-dce(11), v35-dce(12), v36-dce(13),
    eia530-dte(14),
    v11-dte(15), v24-dte(16), v35-dte(17), v36-dte(18),
    empty(19), isdn(20), pcmcia-async(21),
    isdn-e1-rj45(22), isdn-e1-bnc(23), isdn-t1-rj45(24) }
CompType ::= INTEGER { proprietary(1), stac(2) }
Direction ::= INTEGER { unknown(1), incoming(2), outgoing(3) }
DataState ::= INTEGER { down(1), timeCut(2), up(3) }
ConnectState ::= INTEGER { create(1), down(2), outgoingCall(3),
    incomingCall(4), incomingDisconnect(5), outgoingDisconnect(6),
    waitDisconnectConfirm(7), error(8), destroy(9), timeCut(10), idle(11),
    up(12), empty(13) }

UserEnum ::= INTEGER { all(1), ip(2), ipx(3), br(4) }
ProtoEnum ::= INTEGER { ip-all(1), ip-ftp(2), ip-telnet(3),
			ip-smtp(4), ip-dns(5), ip-bootp(6),
			ip-http(7), ip-snmp(8), ip-rip(9),
			ip-tunnel(10), ip-other(11), ipx-all(12),
			ipx-ncp(13), ipx-spx(14), ipx-rip(15),
			ipx-sap(16), ipx-type20(17), ipx-other(18),
			br-all(19), br-bpdu(20), br-other(21) }



mpl                OBJECT IDENTIFIER ::= { mib2ext 20 }
  mplService        OBJECT IDENTIFIER ::= { mpl 1 }
  mplLanSpecific    OBJECT IDENTIFIER ::= { mpl 2 }
  mplWanSpecific    OBJECT IDENTIFIER ::= { mpl 3 }
  mplIfSpecific     OBJECT IDENTIFIER ::= { mpl 4 }
  mplGeneral        OBJECT IDENTIFIER ::= { mpl 5 }
  mplUtilization    OBJECT IDENTIFIER ::= { mpl 6 }



--- Service table


mplServiceTable OBJECT-TYPE
    SYNTAX SEQUENCE OF MplServiceEntry
    ACCESS not-accessible
    STATUS mandatory
    DESCRIPTION
        "This table contains information on MP Links.
        These entries applies to LAN entries as well as
        WAN entries."
    ::= { mplService 1 }

mplServiceEntry OBJECT-TYPE
    SYNTAX MplServiceEntry
    ACCESS not-accessible
    STATUS mandatory
    DESCRIPTION
        "Information on a particular MP Link."
    INDEX { mplServiceNumber }
    ::= { mplServiceTable 1 }

MplServiceEntry ::=
    SEQUENCE {
        mplServiceNumber
            INTEGER,
        mplServiceSlotNumber
            INTEGER,
        mplServicePlugNumber
            INTEGER,
        mplServicePlugName
            DisplayString,
        mplServiceAttachment
            Attachment,
        mplServiceProvider
            INTEGER,
        mplServiceBytesSentUpper
            Counter,
        mplServiceBytesSentLower
            Counter,
        mplServiceBytesReceivedUpper
            Counter,
        mplServiceBytesReceivedLower
            Counter,
        mplServiceLock
            OnOff
    }


mplServiceNumber OBJECT-TYPE
    SYNTAX INTEGER
    ACCESS read-only
    STATUS mandatory
    DESCRIPTION
        "The MP Link number. The MP Link number is the
        same as the ifIndex for the corresponding
        upper group in the MIB-2 ifGroup."
    ::= { mplServiceEntry 1 }

mplServiceSlotNumber OBJECT-TYPE
    SYNTAX INTEGER
    ACCESS read-only
    STATUS mandatory
    DESCRIPTION
        "The Slot position of the card. Set to 0 for
        stand-alone products."
    ::= { mplServiceEntry 2 }

mplServicePlugNumber OBJECT-TYPE
    SYNTAX INTEGER
    ACCESS read-only
    STATUS mandatory
    DESCRIPTION
        "The plug number of the physical interface to
        which the MP Link is associated."
    ::= { mplServiceEntry 3 }

mplServicePlugName OBJECT-TYPE
    SYNTAX DisplayString (SIZE (1..30))
    ACCESS read-only
    STATUS mandatory
    DESCRIPTION
        "The name of the physical interface to which
        the MP Link is associated."
    ::= { mplServiceEntry 4 }

mplServiceAttachment OBJECT-TYPE
    SYNTAX Attachment
    ACCESS read-only
    STATUS mandatory
    DESCRIPTION
        "The connector type used to connect the router
        to the LAN or WAN."
    ::= { mplServiceEntry 5 }

mplServiceProvider OBJECT-TYPE
    SYNTAX INTEGER { lan(1), lapbHdlc(2), pppHdlc(3), frHdlc(4),
                     frAttachment(5), lapbIsdn(6), pppIsdn(7),
                     isdnAttachment(8), x25Lapb(9), x25Attachment(10),
                     slip(11), pppMultiMaster(12), pppAodi(13),
		     pppX25(14), pppPcmcia(15), pppTcpTunnel(16),
		     pppPcmciaModem(17), padX25(18), pppAsync(19),
		     asyncAttachment(20), pppX31(21) }
    ACCESS read-only
    STATUS mandatory
    DESCRIPTION
        "The type of provider for this MP Link. For WAN
        links this specifies the actual protocol
        stack."
    ::= { mplServiceEntry 6 }

mplServiceBytesSentUpper OBJECT-TYPE
    SYNTAX Counter
    ACCESS read-only
    STATUS mandatory
    DESCRIPTION
        "The upper 32 bits of the 64 bits counter which
        is the number of octets (bytes) sent via the MP
        Link."
    ::= { mplServiceEntry 7 }

mplServiceBytesSentLower OBJECT-TYPE
    SYNTAX Counter
    ACCESS read-only
    STATUS mandatory
    DESCRIPTION
        "The lower 32 bits of the 64 bits counter which
        is the number of octets (bytes) sent via the MP
        Link."
    ::= { mplServiceEntry 8 }

mplServiceBytesReceivedUpper OBJECT-TYPE
    SYNTAX Counter
    ACCESS read-only
    STATUS mandatory
    DESCRIPTION
        "The lower 32 bits of the 64 bits counter which
        is the number of octets (bytes) sent via the MP
        Link."
    ::= { mplServiceEntry 9 }

mplServiceBytesReceivedLower OBJECT-TYPE
    SYNTAX Counter
    ACCESS read-only
    STATUS mandatory
    DESCRIPTION
        "The lower 32 bits of the 64 bits counter which
        is the number of octets (bytes) received via
        the MP Link."
    ::= { mplServiceEntry 10 }

mplServiceLock OBJECT-TYPE
    SYNTAX OnOff
    ACCESS read-write
    STATUS mandatory
    DESCRIPTION
        "Indicates whether an MP Link has been locked
        from local management. The link may be unlocked
        by setting the value to 'off' and locked by
        setting the value to 'on'."
    ::= { mplServiceEntry 11 }


--- LAN table

mplLanTable OBJECT-TYPE
    SYNTAX SEQUENCE OF MplLanEntry
    ACCESS not-accessible
    STATUS mandatory
    DESCRIPTION
        "This table contains information on LAN MP
        Links."
    ::= { mplLanSpecific 1 }

mplLanEntry OBJECT-TYPE
    SYNTAX MplLanEntry
    ACCESS not-accessible
    STATUS mandatory
    DESCRIPTION
        "Information on a particular LAN MP Link."
    INDEX { mplLanNumber }
    ::= { mplLanTable 1 }

MplLanEntry ::=
    SEQUENCE {
        mplLanNumber
            INTEGER,
        mplLanRxCRCErrors
            Counter,
        mplLanRxOverrun
            Counter,
        mplLanRxLong
            Counter,
        mplLanRxOverflow
            Counter,
        mplLanRxAlnErrors
            Counter,
        mplLanRxOuts
            Counter,
        mplLanRxShort
            Counter,
        mplLanTxDeferred
            Counter,
        mplLanTxUnderrun
            Counter,
        mplLanTxSQEFailure
            Counter,
        mplLanTxExcDeferral
            Counter,
        mplLanTxCollExceed
            Counter,
        mplLanTxLateColl
            Counter,
        mplLanTxCollisions
            Counter,
        mplLanTxNoCarrier
            Counter
    }

mplLanNumber OBJECT-TYPE
    SYNTAX INTEGER
    ACCESS read-only
    STATUS mandatory
    DESCRIPTION
        "The LAN MP Link number. The MP Link number is
        the same as the ifIndex for the corresponding
        upper group in the MIB-2 ifGroup."
    ::= { mplLanEntry 1 }

mplLanRxCRCErrors OBJECT-TYPE
    SYNTAX Counter
    ACCESS read-only
    STATUS mandatory
    DESCRIPTION
        "The number of frames received which were
        discarded due to Cyclic Redundancy Check (CRC)
        errors."
    ::= { mplLanEntry 2 }

mplLanRxOverrun OBJECT-TYPE
    SYNTAX Counter
    ACCESS read-only
    STATUS mandatory
    DESCRIPTION
        "The number of frames received which were lost
        due to RAM overloads within the router. This
        should not occur."
    ::= { mplLanEntry 3 }

mplLanRxLong OBJECT-TYPE
    SYNTAX Counter
    ACCESS read-only
    STATUS mandatory
    DESCRIPTION
        "The number of frames received which were
        discarded due to being larger than the maximum
        allowable length on the LAN."
    ::= { mplLanEntry 4 }

mplLanRxOverflow OBJECT-TYPE
    SYNTAX Counter
    ACCESS read-only
    STATUS mandatory
    DESCRIPTION
        "The number of frames received which were
        discarded due to lack of buffer capacity."
    ::= { mplLanEntry 5 }

mplLanRxAlnErrors OBJECT-TYPE
    SYNTAX Counter
    ACCESS read-only
    STATUS mandatory
    DESCRIPTION
        "The number of frames received which were
        discarded due to having the wrong frame
        length."
    ::= { mplLanEntry 6 }

mplLanRxOuts OBJECT-TYPE
    SYNTAX Counter
    ACCESS read-only
    STATUS mandatory
    DESCRIPTION
        "The number of frames received which were
        processed by higher layer protocols."
    ::= { mplLanEntry 7 }

mplLanRxShort OBJECT-TYPE
    SYNTAX Counter
    ACCESS read-only
    STATUS mandatory
    DESCRIPTION
        "The number of frames received which were
        discarded due to being shorter than the smallest
        allowable length on the LAN."
    ::= { mplLanEntry 8 }

mplLanTxDeferred OBJECT-TYPE
    SYNTAX Counter
    ACCESS read-only
    STATUS mandatory
    DESCRIPTION
        "The number of outgoing frames which were
        discarded due to a busy link."
    ::= { mplLanEntry 9 }

mplLanTxUnderrun OBJECT-TYPE
    SYNTAX Counter
    ACCESS read-only
    STATUS mandatory
    DESCRIPTION
        "The number of outgoing frames which were
        discarded due to overload."
    ::= { mplLanEntry 10 }

mplLanTxSQEFailure OBJECT-TYPE
    SYNTAX Counter
    ACCESS read-only
    STATUS mandatory
    DESCRIPTION
        "The number of outbound frames which had
        Signal Quality Errors (SQE)."
    ::= { mplLanEntry 11 }

mplLanTxExcDeferral OBJECT-TYPE
    SYNTAX Counter
    ACCESS read-only
    STATUS mandatory
    DESCRIPTION
        "The number of transmission attempts which were delayed
        for more than 3.2 ms."
    ::= { mplLanEntry 12 }

mplLanTxCollExceed OBJECT-TYPE
    SYNTAX Counter
    ACCESS read-only
    STATUS mandatory
    DESCRIPTION
        "The number of outbound frames which were
        discarded due to exceeding 16 collisions on the
        Ethernet."
    ::= { mplLanEntry 13 }

mplLanTxLateColl OBJECT-TYPE
    SYNTAX Counter
    ACCESS read-only
    STATUS mandatory
    DESCRIPTION
        "The number of collisions occurring after the
        first 512 bytes of a frame had been
        transmitted."
    ::= { mplLanEntry 14 }

mplLanTxCollisions OBJECT-TYPE
    SYNTAX Counter
    ACCESS read-only
    STATUS mandatory
    DESCRIPTION
        "The number of outgoing frames which were
        discarded due to collisions that occurred
        during transmissions."
    ::= { mplLanEntry 15 }

mplLanTxNoCarrier OBJECT-TYPE
    SYNTAX Counter
    ACCESS read-only
    STATUS mandatory
    DESCRIPTION
        "The number of No Carrier detections during
        transmissions."
    ::= { mplLanEntry 16 }


--- WAN table


mplWanTable OBJECT-TYPE
    SYNTAX SEQUENCE OF MplWanEntry
    ACCESS not-accessible
    STATUS mandatory
    DESCRIPTION
        "This table contains information on WAN MP
        Links."
    ::= { mplWanSpecific 1 }

mplWanEntry OBJECT-TYPE
    SYNTAX MplWanEntry
    ACCESS not-accessible
    STATUS mandatory
    DESCRIPTION
        "Information on a particular WAN MP Link."
    INDEX { mplWanNumber }
    ::= { mplWanTable 1 }

MplWanEntry ::= SEQUENCE {
        mplWanNumber
            INTEGER,
        mplWanDataState
            DataState,
        mplWanDataStateTimer
            INTEGER,
        mplWanConnectState
            ConnectState,
        mplWanConnectStateTimer
            INTEGER,
        mplWanCompression
            OnOff,
        mplWanCompressionType
            CompType,
        mplWanCallsSucceeded
            Counter,
        mplWanCallsFailed
            Counter,
        mplWanCallsAccepted
            Counter,
        mplWanCallsRejected
            Counter,
        mplWanRetries
            INTEGER,
        mplWanDirection
            Direction,
        mplWanHasBackup
            OnOff,
        mplWanBackupFor
            INTEGER,
        mplWanBackupForAttachment
             OnOff,
        mplWanFlags
            INTEGER,
        mplWanPppMaster
            INTEGER,
        mplWanPppSlaveUpCount
            INTEGER,
        mplWanActivityTimeLeft
            INTEGER,
        mplWanActivity
            OnOff,
        mplWanTimer
            OnOff,
        mplWanTimeTillTimecut
            OnOff,
	mplWanLastPacket
            OCTET STRING,
        mplWanInCallsPlaced
            Counter,
        mplWanOutCallsPlaced
            Counter,
        mplWanInTimeActive
            INTEGER,
        mplWanOutTimeActive
            INTEGER,
        mplWanTotalTime
            INTEGER
    }

mplWanNumber OBJECT-TYPE
    SYNTAX INTEGER
    ACCESS read-only
    STATUS mandatory
    DESCRIPTION
        "The WAN MP Link number. The MP Link number is
        the same as the ifIndex for the corresponding
        upper group in the MIB-2 ifGroup."
    ::= { mplWanEntry 1 }

mplWanDataState OBJECT-TYPE
    SYNTAX DataState
    ACCESS read-only
    STATUS mandatory
    DESCRIPTION
        "The state of the MP Link seen from the higher
        layer protocol."
    ::= { mplWanEntry 2 }

mplWanDataStateTimer OBJECT-TYPE
    SYNTAX INTEGER
    ACCESS read-only
    STATUS mandatory
    DESCRIPTION
        "The time in seconds since the MP Link entered
        the Data State."
    ::= { mplWanEntry 3 }

mplWanConnectState OBJECT-TYPE
    SYNTAX ConnectState
    ACCESS read-only
    STATUS mandatory
    DESCRIPTION
        "Indicates the connection state of the WAN MP
        Link."
    ::= { mplWanEntry 4 }

mplWanConnectStateTimer OBJECT-TYPE
    SYNTAX INTEGER
    ACCESS read-only
    STATUS mandatory
    DESCRIPTION
        "The time in seconds since the MP Link entered
        the Connect State."
    ::= { mplWanEntry 5 }

mplWanCompression OBJECT-TYPE
    SYNTAX OnOff
    ACCESS read-only
    STATUS mandatory
    DESCRIPTION
        "Indicates if data compression is used over the
        WAN MP Link. For frame relay links compression
        is not negotiated. For all other WAN protocols
        the compression will remain 'off' if not
        configured in both routers over the link."
    ::= { mplWanEntry 6 }

mplWanCompressionType OBJECT-TYPE
    SYNTAX CompType
    ACCESS read-only
    STATUS mandatory
    DESCRIPTION
        "Proprietary compression is used for LAPB and
        X.25 MP Links. For all other WAN protocols the
        Stac compression algorithm is used."
    ::= { mplWanEntry 7 }

mplWanCallsSucceeded OBJECT-TYPE
    SYNTAX Counter
    ACCESS read-only
    STATUS mandatory
    DESCRIPTION
        "The number of outgoing call which succeeded in
        making the connection."
    ::= { mplWanEntry 8 }

mplWanCallsFailed OBJECT-TYPE
    SYNTAX Counter
    ACCESS read-only
    STATUS mandatory
    DESCRIPTION
        "The number of outgoing call which failed to
        make the connection."
    ::= { mplWanEntry 9 }

mplWanCallsAccepted OBJECT-TYPE
    SYNTAX Counter
    ACCESS read-only
    STATUS mandatory
    DESCRIPTION
        "The number of incoming calls which were
        accepted on this link."
    ::= { mplWanEntry 10 }

mplWanCallsRejected OBJECT-TYPE
    SYNTAX Counter
    ACCESS read-only
    STATUS mandatory
    DESCRIPTION
        "The number of incoming calls which were
        rejected on this link."
    ::= { mplWanEntry 11 }

mplWanRetries OBJECT-TYPE
    SYNTAX INTEGER
    ACCESS read-write
    STATUS mandatory
    DESCRIPTION
        "The number of retries made for outgoing
        calls. May be set to zero which causes the
        call sequence to restarted."
    ::= { mplWanEntry 12 }

mplWanDirection OBJECT-TYPE
    SYNTAX Direction
    ACCESS read-only
    STATUS mandatory
    DESCRIPTION
        "Shows who initiated the call. 'incoming' if the
        call was initiated by the remote router and
        'outgoing' if the call was inititated by this
        router. For PPP Multi Links the direction
        refers the the direction of the first slave
        link."
    ::= { mplWanEntry 13 }

mplWanHasBackup OBJECT-TYPE
    SYNTAX OnOff
    ACCESS read-only
    STATUS mandatory
    DESCRIPTION
        "Indicates whether this link has a backup link
        configured for it."
    ::= { mplWanEntry 14 }

mplWanBackupFor OBJECT-TYPE
    SYNTAX INTEGER
    ACCESS read-only
    STATUS mandatory
    DESCRIPTION
        "Shows the primary link for which this link is
        the backup. The value 0 indicates that this is
        not a backup link."
    ::= { mplWanEntry 15 }

mplWanBackupForAttachment OBJECT-TYPE
    SYNTAX OnOff
    ACCESS read-only
    STATUS mandatory
    DESCRIPTION
        "Indicates whether this link is a backup for an
        attachment."
    ::= { mplWanEntry 16 }

mplWanFlags OBJECT-TYPE
    SYNTAX INTEGER
    ACCESS read-only
    STATUS mandatory
    DESCRIPTION
        "WAN Flags
           dataCompressionMask 0x0001
           acceptIncomingMask  0x0002
           permitOutgoingMask  0x0004
           permitTimeCutMask   0x0008
           chapMask            0x0010 - CHAP, PPP only
           papMask             0x0020 - PAP, PPP only
           onlyReplyChapMask   0x0040
           slaveLink           0x0080
           blockOutgoing       0x0100
           blockIncoming       0x0200
           isLeased            0x0400
           dataCompressionMode 0x0800 - PPP new-stac compression flag
           activitySoft        0x1000 - Activity timer only sends trap"
    ::= { mplWanEntry 17 }

mplWanPppMaster OBJECT-TYPE
    SYNTAX INTEGER
    ACCESS read-only
    STATUS mandatory
    DESCRIPTION
        "Indicates the master link for a slave link.
        For master links and links not associated with
        a PPP Multi Link the value is 0."
    ::= { mplWanEntry 18 }

mplWanPppSlaveUpCount OBJECT-TYPE
    SYNTAX INTEGER
    ACCESS read-only
    STATUS mandatory
    DESCRIPTION
        "The number of slave links in Connect State
        'up'. For slave links and links not associated
        with a PPP Multi Link the value is 1."
    ::= { mplWanEntry 19 }

mplWanActivityTimeLeft OBJECT-TYPE
    SYNTAX INTEGER
    ACCESS read-only
    STATUS mandatory
    DESCRIPTION
        "The time remaining in seconds until the Daily
        Activity Limit will close and lock the link.
        When the Daily Activity Limit has been reached,
        the link can be activated by setting
        mplWanActivity to 'on'."
    ::= { mplWanEntry 20 }

mplWanActivity OBJECT-TYPE
    SYNTAX OnOff
    ACCESS read-write
    STATUS mandatory
    DESCRIPTION
        "Indicates whether the Daily Activity Limit has
        been reached and locked the link. To unlock the
        link set the value to 'off'. It is not possible
        to set to the value to 'on'."
    ::= { mplWanEntry 21 }

mplWanTimer OBJECT-TYPE
    SYNTAX OnOff
    ACCESS read-only
    STATUS mandatory
    DESCRIPTION
        "Indicates whether an MP Link timer has locked
        the link. 'on' means the link is locked."
    ::= { mplWanEntry 22 }

mplWanTimeTillTimecut OBJECT-TYPE
    SYNTAX INTEGER
    ACCESS read-only
    STATUS mandatory
    DESCRIPTION
        "Time left in seconds until time cut"
    ::= { mplWanEntry 23 }

mplWanLastPacket OBJECT-TYPE
    SYNTAX OCTET STRING (SIZE(64))
    ACCESS read-only
    STATUS mandatory
    DESCRIPTION
        "The first byte in this string identifies the type of packet that
         opened the link the last time.

	   IP              1       Internet Protocols      0xcc
	   IPX             2       Novell IPX      0x800000008137
	   STA_ETH         3       Bridge-Ether    0x800080c20007
	   STA_FRAG        4       Bridge-Frag     0x800080c2000d
	   STA_BPDU        5       Bridge-BPDU     0x800080c2000e
	   STA_CRAY        6       Bridge-Cray     0x800000800500
	   STA_ETH_FCS    15       Bridge-FCS

        After this byte follows a part of the packet header."
    ::= { mplWanEntry 24 }


mplWanInCallsPlaced OBJECT-TYPE
    SYNTAX Counter
    ACCESS read-only
    STATUS mandatory
    DESCRIPTION
        "??? Number of calls placed."
    ::= { mplWanEntry 25 }


mplWanOutCallsPlaced OBJECT-TYPE
    SYNTAX Counter
    ACCESS read-only
    STATUS mandatory
    DESCRIPTION
        "??? Number of calls placed."
    ::= { mplWanEntry 26 }


mplWanInTimeActive OBJECT-TYPE
    SYNTAX INTEGER
    ACCESS read-only
    STATUS mandatory
    DESCRIPTION
        "The time in seconds that the link was in the Up state for
         incoming calls."
    ::= { mplWanEntry 27 }


mplWanOutTimeActive OBJECT-TYPE
    SYNTAX INTEGER
    ACCESS read-only
    STATUS mandatory
    DESCRIPTION
        "The time in seconds that the link was in the Up state for
         outcoming calls."
    ::= { mplWanEntry 28 }


mplWanTotalTime OBJECT-TYPE
    SYNTAX INTEGER
    ACCESS read-only
    STATUS mandatory
    DESCRIPTION
        "??? "
    ::= { mplWanEntry 29 }



--- WAN Compression table


mplCompTable OBJECT-TYPE
    SYNTAX SEQUENCE OF MplCompEntry
    ACCESS not-accessible
    STATUS mandatory
    DESCRIPTION "Compression table with counters and other information
    regarding the Transmit and Receive Decoder."
    ::= { mplWanSpecific 2 }

mplCompEntry OBJECT-TYPE
    SYNTAX MplCompEntry
    ACCESS not-accessible
    STATUS mandatory
    DESCRIPTION ""
    INDEX { mplCompNumber }
    ::= { mplCompTable 1 }

MplCompEntry ::= SEQUENCE {
                        mplCompNumber
                           INTEGER,
                        mplCompRxDecRxBytesTotalUpper
                           Counter,
                        mplCompRxDecRxBytesTotalLower
                           Counter,
                        mplCompRxDecRxBytesDecompUpper
                           Counter,
                        mplCompRxDecRxBytesDecompLower
                           Counter,
                        mplCompRxDecDecompressedUpper
                           Counter,
                        mplCompRxDecDecompressedLower
                           Counter,
                        mplCompRxDecAllocErrorsUpper
                           Counter,
                        mplCompRxDecAllocErrorsLower
                           Counter,
                        mplCompRxDecRemoteInits
                           Counter,
                        mplCompTxEncInBytesTotalUpper
                           Counter,
                        mplCompTxEncInBytesTotalLower
                           Counter,
                        mplCompTxEncTxBytesCompUpper
                           Counter,
                        mplCompTxEncTxBytesCompLower
                           Counter,
                        mplCompTxEncCompressedUpper
                           Counter,
                        mplCompTxEncCompressedLower
                           Counter,
                        mplCompTxEncAllocErrorsUpper
                           Counter,
                        mplCompTxEncAllocErrorsLower
                           Counter,
                        mplCompTxEncLocalInits
                           Counter,
                        mplCompTxEncTransmitErrors
                           INTEGER,
                        mplCompTxEncQueueLength
                           INTEGER
                        }

mplCompNumber OBJECT-TYPE
    SYNTAX INTEGER
    ACCESS read-only
    STATUS mandatory
    DESCRIPTION "The WAN MP Link number. The MP Link number is
                 the same as the ifIndex for the corresponding
                 upper group in the MIB-2 ifGroup."
    ::= { mplCompEntry 1 }

mplCompRxDecRxBytesTotalUpper OBJECT-TYPE
    SYNTAX Counter
    ACCESS read-only
    STATUS mandatory
    DESCRIPTION
       "The upper 32 bits of the 64 bits counter which is the number of
        bytes received by the Receive Decoder."
    ::= { mplCompEntry 2 }

mplCompRxDecRxBytesTotalLower OBJECT-TYPE
    SYNTAX Counter
    ACCESS read-only
    STATUS mandatory
    DESCRIPTION
       "The lower 32 bits of the 64 bits counter which is the number of
        bytes received by the Receive Decoder."
    ::= { mplCompEntry 3 }

mplCompRxDecRxBytesDecompUpper OBJECT-TYPE
    SYNTAX Counter
    ACCESS read-only
    STATUS mandatory
    DESCRIPTION
       "The upper 32 bits of the 64 bits counter which is the number of
        bytes sent by the Receive Decoder."
    ::= { mplCompEntry 4 }

mplCompRxDecRxBytesDecompLower OBJECT-TYPE
    SYNTAX Counter
    ACCESS read-only
    STATUS mandatory
    DESCRIPTION
       "The lower 32 bits of the 64 bits counter which is the number of
        bytes sent by the Receive Decoder."
    ::= { mplCompEntry 5 }

mplCompRxDecDecompressedUpper OBJECT-TYPE
    SYNTAX Counter
    ACCESS read-only
    STATUS mandatory
    DESCRIPTION
       "The upper 32 bits of the 64 bits counter which is the number of
        packets decompressed by the Receive Decoder."
    ::= { mplCompEntry 6 }

mplCompRxDecDecompressedLower OBJECT-TYPE
    SYNTAX Counter
    ACCESS read-only
    STATUS mandatory
    DESCRIPTION
       "The lower 32 bits of the 64 bits counter which is the number of
        packets decompressed by the Receive Decoder."
    ::= { mplCompEntry 7 }

mplCompRxDecAllocErrorsUpper OBJECT-TYPE
    SYNTAX Counter
    ACCESS read-only
    STATUS mandatory
    DESCRIPTION
       "The upper 32 bits of the 64 bits counter which is the number of
        allocation errors in the Receive Decoder."
    ::= { mplCompEntry 8 }

mplCompRxDecAllocErrorsLower OBJECT-TYPE
    SYNTAX Counter
    ACCESS read-only
    STATUS mandatory
    DESCRIPTION
       "The lower 32 bits of the 64 bits counter which is the number of
        allocation errors in the Receive Decoder."
    ::= { mplCompEntry 9 }

mplCompRxDecRemoteInits OBJECT-TYPE
    SYNTAX Counter
    ACCESS read-only
    STATUS mandatory
    DESCRIPTION "Number of remote initializations by the Receive Decoder."
    ::= { mplCompEntry 10 }

mplCompTxEncInBytesTotalUpper OBJECT-TYPE
    SYNTAX Counter
    ACCESS read-only
    STATUS mandatory
    DESCRIPTION
       "The upper 32 bits of the 64 bits counter which is the number of
        bytes received by the Transmit Decoder."
    ::= { mplCompEntry 11 }

mplCompTxEncInBytesTotalLower OBJECT-TYPE
    SYNTAX Counter
    ACCESS read-only
    STATUS mandatory
    DESCRIPTION
       "The lower 32 bits of the 64 bits counter which is the number of
        bytes received by the Transmit Decoder."
    ::= { mplCompEntry 12 }

mplCompTxEncTxBytesCompUpper OBJECT-TYPE
    SYNTAX Counter
    ACCESS read-only
    STATUS mandatory
    DESCRIPTION
       "The upper 32 bits of the 64 bits counter which is the number of
        bytes sent by the Transmit Decoder."
    ::= { mplCompEntry 13 }

mplCompTxEncTxBytesCompLower OBJECT-TYPE
    SYNTAX Counter
    ACCESS read-only
    STATUS mandatory
    DESCRIPTION
       "The lower 32 bits of the 64 bits counter which is the number of
        bytes sent by the Transmit Decoder."
    ::= { mplCompEntry 14 }

mplCompTxEncCompressedUpper OBJECT-TYPE
    SYNTAX Counter
    ACCESS read-only
    STATUS mandatory
    DESCRIPTION
       "The upper 32 bits of the 64 bits counter which is the number of
        packets compressed by the Transmit Decoder."
    ::= { mplCompEntry 15 }

mplCompTxEncCompressedLower OBJECT-TYPE
    SYNTAX Counter
    ACCESS read-only
    STATUS mandatory
    DESCRIPTION
       "The lower 32 bits of the 64 bits counter which is the number of
        packets compressed by the Transmit Decoder."
    ::= { mplCompEntry 16 }

mplCompTxEncAllocErrorsUpper OBJECT-TYPE
    SYNTAX Counter
    ACCESS read-only
    STATUS mandatory
    DESCRIPTION
       "The upper 32 bits of the 64 bits counter which is the number of
        allocation errors in the Transmit Decoder."
    ::= { mplCompEntry 17 }

mplCompTxEncAllocErrorsLower OBJECT-TYPE
    SYNTAX Counter
    ACCESS read-only
    STATUS mandatory
    DESCRIPTION
       "The lower 32 bits of the 64 bits counter which is the number of
        allocation errors in the Transmit Decoder."
    ::= { mplCompEntry 18 }

mplCompTxEncLocalInits OBJECT-TYPE
    SYNTAX Counter
    ACCESS read-only
    STATUS mandatory
    DESCRIPTION "Number of local initializations by the Receive Decoder."
    ::= { mplCompEntry 19 }

mplCompTxEncTransmitErrors OBJECT-TYPE
    SYNTAX INTEGER
    ACCESS read-only
    STATUS mandatory
    DESCRIPTION "Number of transmit errors"
    ::= { mplCompEntry 20 }

mplCompTxEncQueueLength OBJECT-TYPE
    SYNTAX INTEGER
    ACCESS read-only
    STATUS mandatory
    DESCRIPTION "Queue length"
    ::= { mplCompEntry 21 }



--- IfStackTable

mplIfStackTable  OBJECT-TYPE
    SYNTAX SEQUENCE OF MplIfStackEntry
    ACCESS not-accessible
    STATUS mandatory
    DESCRIPTION
        "This table contains information on the relationships
        between the multiple sub-layers of network interfaces.
        In particular, it contains information on which sub-
        layers run 'on top of' which other sub-layers.  Each
        sub-layer corresponds to a conceptual row in the
        ifTable."
    ::= { mplIfSpecific 1 }


mplIfStackEntry  OBJECT-TYPE
    SYNTAX MplIfStackEntry
    ACCESS not-accessible
    STATUS mandatory
    DESCRIPTION
        "Information on a particular relationship between two
        sub-layers, specifying that one sub-layer runs on
        'top' of the other sub-layer.  Each sub-layer
        corresponds to a conceptual row in the ifTable."
    INDEX { mplIfStackNumber }
    ::= { mplIfStackTable 1 }


MplIfStackEntry ::=
    SEQUENCE {
        mplIfStackNumber       INTEGER,
        mplIfStackLowerLayer   INTEGER
    }


mplIfStackNumber  OBJECT-TYPE
    SYNTAX INTEGER
    ACCESS read-only
    STATUS mandatory
    DESCRIPTION
        "The MP Link number. The MP Link number is the
        same as the ifIndex for the corresponding
        upper group in the MIB-2 ifGroup."
    ::= { mplIfStackEntry 1 }


mplIfStackLowerLayer  OBJECT-TYPE
    SYNTAX INTEGER
    ACCESS read-only
    STATUS mandatory
    DESCRIPTION
        "The value of ifIndex corresponding to the lower sub-
        layer of the relationship, i.e., the sub-layer which
        runs 'below' the sub-layer identified by the
        corresponding instance of mplIfStackNumber.  If
        there is no lower sub-layer, then this object has the
        value 0."
    ::= { mplIfStackEntry 2 }


--- General

mplGeneralOverviewChange  OBJECT-TYPE
    SYNTAX TimeTicks
    ACCESS read-only
    STATUS mandatory
    DESCRIPTION
        "The value of sysUpTime at the time any MP Link
        seen from the overview changed state or the
        like."
    ::= { mplGeneral 1 }


mplGeneralIfgroupStatus  OBJECT-TYPE
    SYNTAX OCTET STRING (SIZE(255))
    ACCESS read-only
    STATUS mandatory
    DESCRIPTION
        "A table describing the status of all ifgroups.
        Bit 0-3: State: 001 = Up, 010 = Down, 011 = Timecut, 100 = Disabled
	                111 = Lock.
        Bit 4:   Reserved for future use
        Bit 5:   IP status: 1 = Up, 0 = Down.
          (This bit is only used for MPLinks)
        Bit 6:   IPX status: 1 = Up, 0 = Down.
          (This bit is only used for MPLinks)
        Bit 7:   Bridge status: 1 = Up,  0 = Down.
          (This bit is only used for MPLinks)"
    ::= { mplGeneral 2 }

--- Utilization

mplUtilizationTable OBJECT-TYPE
    SYNTAX SEQUENCE OF MplUtilizationEntry
    ACCESS not-accessible
    STATUS mandatory
    DESCRIPTION "Utilization table"
    ::= { mplUtilization 1 }

mplUtilizationEntry OBJECT-TYPE
    SYNTAX MplUtilizationEntry
    ACCESS not-accessible
    STATUS mandatory
    DESCRIPTION ""
    INDEX { mplUtilizationPlugNumber, mplUtilizationMplink, mplUtilizationUser, mplUtilizationProtocol }
    ::= { mplUtilizationTable 1 }

MplUtilizationEntry ::= SEQUENCE {
                        mplUtilizationPlugNumber
                           INTEGER,
                        mplUtilizationMplink
                           INTEGER,
                        mplUtilizationUser
                           UserEnum,
                        mplUtilizationProtocol
                           ProtoEnum,
                        mplUtilizationRxUtil
                           Counter,
                        mplUtilizationTxUtil
                           Counter
                        }

mplUtilizationPlugNumber OBJECT-TYPE
    SYNTAX INTEGER
    ACCESS read-only
    STATUS mandatory
    DESCRIPTION ""
    ::= { mplUtilizationEntry 1 }

mplUtilizationMplink OBJECT-TYPE
    SYNTAX INTEGER
    ACCESS read-only
    STATUS mandatory
    DESCRIPTION ""
    ::= { mplUtilizationEntry 2 }

mplUtilizationUser OBJECT-TYPE
    SYNTAX UserEnum
    ACCESS read-only
    STATUS mandatory
    DESCRIPTION ""
    ::= { mplUtilizationEntry 3 }

mplUtilizationProtocol OBJECT-TYPE
    SYNTAX ProtoEnum
    ACCESS read-only
    STATUS mandatory
    DESCRIPTION ""
    ::= { mplUtilizationEntry 4 }

mplUtilizationRxUtil OBJECT-TYPE
    SYNTAX Counter
    ACCESS read-only
    STATUS mandatory
    DESCRIPTION ""
    ::= { mplUtilizationEntry 5 }

mplUtilizationTxUtil OBJECT-TYPE
    SYNTAX Counter
    ACCESS read-only
    STATUS mandatory
    DESCRIPTION ""
    ::= { mplUtilizationEntry 6 }


--- Trap section

mplLockEvent TRAP-TYPE
    ENTERPRISE  mpl
    VARIABLES   { mplServiceNumber, mplServiceLock }
    DESCRIPTION
        "Lock state changed to <mplServiceLock> for link <mplServiceNumber>.
        This trap is sent when an MP Link is locked or
        unlocked from local management or via SNMP."
::= 1

mplWanRetriesEvent TRAP-TYPE
    ENTERPRISE  mpl
    VARIABLES   { mplWanNumber, mplWanRetries }
    DESCRIPTION
        "Max. retries exceeded (<mplWanRetries>) for link <mplWanNumber>.
        This trap is sent when an MP Link has had more
        failed connect-attempts than allowed in the
        configuration."
::= 2

mplWanActivityEvent TRAP-TYPE
    ENTERPRISE  mpl
    VARIABLES   { mplWanNumber, mplWanActivity }
    DESCRIPTION
        "Daily Activity Limit has been reached. Link <mplWanNumber> locked.
         This trap is sent when the Daily Activity
        Limit has been reached and locked the link."
::= 3

mplWanTimerEvent TRAP-TYPE
    ENTERPRISE  mpl
    VARIABLES   { mplWanNumber, mplWanTimer }
    DESCRIPTION
        "Link timer has changed lock state to <WanTimer> for link <WanNumber>.
        This trap is sent when an MP Link timer has
        locked or unlocked the link."
::= 4


END
