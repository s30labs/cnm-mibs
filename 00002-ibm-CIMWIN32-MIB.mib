CIMWIN32-MIB DEFINITIONS ::= BEGIN

IMPORTS
   OBJECT-TYPE
      FROM RFC-1212

   TRAP-TYPE
      FROM RFC-1215

   win32WMI,
   Boolean, Uint8, Sint8, Uint16, Sint16, Uint32,
   Sint32, Uint64, Sint64, Real32, Real64, String, Datetime
      FROM UMS-MIB;

win32ComputerSystemTable OBJECT-TYPE
   SYNTAX         SEQUENCE OF Win32ComputerSystemEntry
   ACCESS         not-accessible
   STATUS         mandatory
   DESCRIPTION    "The Win32_ComputerSystem class represents a computer system operating in a Win32 environment."
   REFERENCE      "Win32_ComputerSystem"
::= { win32WMI 10 }

win32ComputerSystemEntry OBJECT-TYPE
   SYNTAX         Win32ComputerSystemEntry
   ACCESS         not-accessible
   STATUS         mandatory
   DESCRIPTION    ""
   INDEX          { win32ComputerSystemKeyIndex }
::= { win32ComputerSystemTable 1 }

Win32ComputerSystemEntry ::= SEQUENCE
{
   win32ComputerSystemKeyIndex String,
   win32ComputerSystemAutomaticResetBootOption Boolean,
   win32ComputerSystemAutomaticResetCapability Boolean,
   win32ComputerSystemBootROMSupported Boolean,
   win32ComputerSystemBootupState String,
   win32ComputerSystemCurrentTimeZone Sint16,
   win32ComputerSystemDomain String,
   win32ComputerSystemInfraredSupported Boolean,
   win32ComputerSystemManufacturer String,
   win32ComputerSystemModel String,
   win32ComputerSystemNetworkServerModeEnabled Boolean,
   win32ComputerSystemOEMLogoBitmap Uint8,
   win32ComputerSystemSupportContactDescription String,
   win32ComputerSystemSystemStartupDelay Uint16,
   win32ComputerSystemSystemStartupOptions String,
   win32ComputerSystemSystemStartupSetting Uint8,
   win32ComputerSystemSystemType String,
   win32ComputerSystemUserName String,
   win32ComputerSystemStatus String
}

win32ComputerSystemKeyIndex OBJECT-TYPE
   SYNTAX         String
   ACCESS         read-write
   STATUS         mandatory
   DESCRIPTION    ""
   REFERENCE      "Win32_ComputerSystem.KeyIndex"
::= { win32ComputerSystemEntry 1 }

win32ComputerSystemAutomaticResetBootOption OBJECT-TYPE
   SYNTAX         Boolean
   ACCESS         read-write
   STATUS         mandatory
   DESCRIPTION    "The AutomaticResetBootOption property determines whether the automatic reset boot option is enabled.<P>Values: TRUE or FALSE. If TRUE, the automatic reset boot option is enabled."
   REFERENCE      "Win32_ComputerSystem.AutomaticResetBootOption"
::= { win32ComputerSystemEntry 2 }

win32ComputerSystemAutomaticResetCapability OBJECT-TYPE
   SYNTAX         Boolean
   ACCESS         read-write
   STATUS         mandatory
   DESCRIPTION    "The AutomaticResetCapability property determines whether the automatic reset is enabled.<P>Values: TRUE or FALSE. If TRUE, the automatic reset is enabled."
   REFERENCE      "Win32_ComputerSystem.AutomaticResetCapability"
::= { win32ComputerSystemEntry 3 }

win32ComputerSystemBootROMSupported OBJECT-TYPE
   SYNTAX         Boolean
   ACCESS         read-write
   STATUS         mandatory
   DESCRIPTION    "The BootROMSupported property determines whether a boot ROM is supported.<P>Values: TRUE or FALSE. If TRUE, a boot ROM is supported."
   REFERENCE      "Win32_ComputerSystem.BootROMSupported"
::= { win32ComputerSystemEntry 4 }

win32ComputerSystemBootupState OBJECT-TYPE
   SYNTAX         String
   ACCESS         read-write
   STATUS         mandatory
   DESCRIPTION    "The BootupState property indicates the bootup state of the computer system.<P>Constraints: Must have a value."
   REFERENCE      "Win32_ComputerSystem.BootupState"
::= { win32ComputerSystemEntry 5 }

win32ComputerSystemCurrentTimeZone OBJECT-TYPE
   SYNTAX         Sint16
   ACCESS         read-write
   STATUS         mandatory
   DESCRIPTION    "The CurrentTimeZone property  indicates the number of minutes the unitary computer system is offset from Greenwich Mean Time (GMT). The number is either positive, negative, or zero."
   REFERENCE      "Win32_ComputerSystem.CurrentTimeZone"
::= { win32ComputerSystemEntry 6 }

win32ComputerSystemDomain OBJECT-TYPE
   SYNTAX         String
   ACCESS         read-write
   STATUS         mandatory
   DESCRIPTION    "The Domain property indicates the domain name of the computer system."
   REFERENCE      "Win32_ComputerSystem.Domain"
::= { win32ComputerSystemEntry 7 }

win32ComputerSystemInfraredSupported OBJECT-TYPE
   SYNTAX         Boolean
   ACCESS         read-write
   STATUS         mandatory
   DESCRIPTION    "The InfraredSupported property determines whether an infrared (IR) port exists on the computer system.<P>Values: TRUE or FALSE. If TRUE, an IR port exists."
   REFERENCE      "Win32_ComputerSystem.InfraredSupported"
::= { win32ComputerSystemEntry 8 }

win32ComputerSystemManufacturer OBJECT-TYPE
   SYNTAX         String
   ACCESS         read-write
   STATUS         mandatory
   DESCRIPTION    "The Manufacturer property indicates the name of the computer manufacturer.<P>Example: Seagate"
   REFERENCE      "Win32_ComputerSystem.Manufacturer"
::= { win32ComputerSystemEntry 9 }

win32ComputerSystemModel OBJECT-TYPE
   SYNTAX         String
   ACCESS         read-write
   STATUS         mandatory
   DESCRIPTION    "The Model property indicates the model name of the computer system.<P>Constraints: Must have a value"
   REFERENCE      "Win32_ComputerSystem.Model"
::= { win32ComputerSystemEntry 10 }

win32ComputerSystemNetworkServerModeEnabled OBJECT-TYPE
   SYNTAX         Boolean
   ACCESS         read-write
   STATUS         mandatory
   DESCRIPTION    "The NetworkServerModeEnabled property determines whether Network Server Mode is enabled.<P>Values: TRUE or FALSE. If TRUE, Network Server Mode is enabled."
   REFERENCE      "Win32_ComputerSystem.NetworkServerModeEnabled"
::= { win32ComputerSystemEntry 11 }

win32ComputerSystemOEMLogoBitmap OBJECT-TYPE
   SYNTAX         Uint8
   ACCESS         read-write
   STATUS         mandatory
   DESCRIPTION    ""
   REFERENCE      "Win32_ComputerSystem.OEMLogoBitmap"
::= { win32ComputerSystemEntry 12 }

win32ComputerSystemSupportContactDescription OBJECT-TYPE
   SYNTAX         String
   ACCESS         read-write
   STATUS         mandatory
   DESCRIPTION    "The SupportContactDescription property is an array that indicates the support contact information for the Win32 computer system."
   REFERENCE      "Win32_ComputerSystem.SupportContactDescription"
::= { win32ComputerSystemEntry 13 }

win32ComputerSystemSystemStartupDelay OBJECT-TYPE
   SYNTAX         Uint16
   ACCESS         read-write
   STATUS         mandatory
   DESCRIPTION    ""
   REFERENCE      "Win32_ComputerSystem.SystemStartupDelay"
::= { win32ComputerSystemEntry 14 }

win32ComputerSystemSystemStartupOptions OBJECT-TYPE
   SYNTAX         String
   ACCESS         read-write
   STATUS         mandatory
   DESCRIPTION    "The SystemStartupOptions property is an array that indicates the options for starting up the Win32 computer system.<P>Constraints: Must have a value"
   REFERENCE      "Win32_ComputerSystem.SystemStartupOptions"
::= { win32ComputerSystemEntry 15 }

win32ComputerSystemSystemStartupSetting OBJECT-TYPE
   SYNTAX         Uint8
   ACCESS         read-write
   STATUS         mandatory
   DESCRIPTION    "The SystemStartupSetting property indicates the index into the default start profile. This value is 'calculated' so that it usually returns zero (0) because at write-time, the profile string is physically moved to the top of the list. (This is how Windows NT determines which value is the default.)"
   REFERENCE      "Win32_ComputerSystem.SystemStartupSetting"
::= { win32ComputerSystemEntry 16 }

win32ComputerSystemSystemType OBJECT-TYPE
   SYNTAX         String
   ACCESS         read-write
   STATUS         mandatory
   DESCRIPTION    "The SystemType property indicates the type of system running on the Win32 computer.<P>Constraints: Must have a value"
   REFERENCE      "Win32_ComputerSystem.SystemType"
::= { win32ComputerSystemEntry 17 }

win32ComputerSystemUserName OBJECT-TYPE
   SYNTAX         String
   ACCESS         read-write
   STATUS         mandatory
   DESCRIPTION    "The UserName property indicates the name of the currently-logged-on user.<P>Constraints: Must have a value<P>Example: John Smith"
   REFERENCE      "Win32_ComputerSystem.UserName"
::= { win32ComputerSystemEntry 18 }

win32ComputerSystemStatus OBJECT-TYPE
   SYNTAX         String
   ACCESS         read-write
   STATUS         mandatory
   DESCRIPTION    "The Status property is a string indicating the current status of the object. Various operational and non-operational statuses can be defined. Operational statuses are OK, Degraded and Pred Fail. Pred Fail indicates that an element may be functioning properly but predicting a failure in the near future. An example is a SMART-enabled hard drive. Non-operational statuses can also be specified. These are Error, Starting, Stopping and Service. The latter, Service, could apply during mirror-resilvering of a disk, reload of a user permissions list, or other administrative work. Not all such work is on-line, yet the managed element is neither OK nor in one of the other states."
   REFERENCE      "Win32_ComputerSystem.Status"
::= { win32ComputerSystemEntry 19 }

win32TapeDriveTable OBJECT-TYPE
   SYNTAX         SEQUENCE OF Win32TapeDriveEntry
   ACCESS         not-accessible
   STATUS         mandatory
   DESCRIPTION    "The Win32_TapeDrive class represents a tape drive on a Win32 system."
   REFERENCE      "Win32_TapeDrive"
::= { win32WMI 20 }

win32TapeDriveEntry OBJECT-TYPE
   SYNTAX         Win32TapeDriveEntry
   ACCESS         not-accessible
   STATUS         mandatory
   DESCRIPTION    ""
   INDEX          { win32TapeDriveKeyIndex }
::= { win32TapeDriveTable 1 }

Win32TapeDriveEntry ::= SEQUENCE
{
   win32TapeDriveKeyIndex String,
   win32TapeDriveCompression Uint32,
   win32TapeDriveECC Uint32,
   win32TapeDriveFeaturesHigh Uint32,
   win32TapeDriveFeaturesLow Uint32,
   win32TapeDriveMediaType String,
   win32TapeDriveReportSetMarks Uint32,
   win32TapeDriveStatus String
}

win32TapeDriveKeyIndex OBJECT-TYPE
   SYNTAX         String
   ACCESS         read-write
   STATUS         mandatory
   DESCRIPTION    ""
   REFERENCE      "Win32_TapeDrive.KeyIndex"
::= { win32TapeDriveEntry 1 }

win32TapeDriveCompression OBJECT-TYPE
   SYNTAX         Uint32
   ACCESS         read-write
   STATUS         mandatory
   DESCRIPTION    "The Compression property indicates the compression level for the tape drive."
   REFERENCE      "Win32_TapeDrive.Compression"
::= { win32TapeDriveEntry 2 }

win32TapeDriveECC OBJECT-TYPE
   SYNTAX         Uint32
   ACCESS         read-write
   STATUS         mandatory
   DESCRIPTION    ""
   REFERENCE      "Win32_TapeDrive.ECC"
::= { win32TapeDriveEntry 3 }

win32TapeDriveFeaturesHigh OBJECT-TYPE
   SYNTAX         Uint32
   ACCESS         read-write
   STATUS         mandatory
   DESCRIPTION    ""
   REFERENCE      "Win32_TapeDrive.FeaturesHigh"
::= { win32TapeDriveEntry 4 }

win32TapeDriveFeaturesLow OBJECT-TYPE
   SYNTAX         Uint32
   ACCESS         read-write
   STATUS         mandatory
   DESCRIPTION    ""
   REFERENCE      "Win32_TapeDrive.FeaturesLow"
::= { win32TapeDriveEntry 5 }

win32TapeDriveMediaType OBJECT-TYPE
   SYNTAX         String
   ACCESS         read-write
   STATUS         mandatory
   DESCRIPTION    "MediaType is the type of media used or accessed by this device."
   REFERENCE      "Win32_TapeDrive.MediaType"
::= { win32TapeDriveEntry 6 }

win32TapeDriveReportSetMarks OBJECT-TYPE
   SYNTAX         Uint32
   ACCESS         read-write
   STATUS         mandatory
   DESCRIPTION    ""
   REFERENCE      "Win32_TapeDrive.ReportSetMarks"
::= { win32TapeDriveEntry 7 }

win32TapeDriveStatus OBJECT-TYPE
   SYNTAX         String
   ACCESS         read-write
   STATUS         mandatory
   DESCRIPTION    "The Status property is a string indicating the current status of the object. Various operational and non-operational statuses can be defined. Operational statuses are OK, Degraded and Pred Fail. Pred Fail indicates that an element may be functioning properly but predicting a failure in the near future. An example is a SMART-enabled hard drive. Non-operational statuses can also be specified. These are Error, Starting, Stopping and Service. The latter, Service, could apply during mirror-resilvering of a disk, reload of a user permissions list, or other administrative work. Not all such work is on-line, yet the managed element is neither OK nor in one of the other states."
   REFERENCE      "Win32_TapeDrive.Status"
::= { win32TapeDriveEntry 8 }

win32DiskDriveTable OBJECT-TYPE
   SYNTAX         SEQUENCE OF Win32DiskDriveEntry
   ACCESS         not-accessible
   STATUS         mandatory
   DESCRIPTION    "The Win32_DiskDrive class represents a physical disk drive as seen by a Win32 operating system. Any interface to a Win32 physical drive is a descendent (or member) of this class.<P>Example: IDE Fixed Disk"
   REFERENCE      "Win32_DiskDrive"
::= { win32WMI 30 }

win32DiskDriveEntry OBJECT-TYPE
   SYNTAX         Win32DiskDriveEntry
   ACCESS         not-accessible
   STATUS         mandatory
   DESCRIPTION    ""
   INDEX          { win32DiskDriveKeyIndex }
::= { win32DiskDriveTable 1 }

Win32DiskDriveEntry ::= SEQUENCE
{
   win32DiskDriveKeyIndex String,
   win32DiskDriveBytesPerSector Uint32,
   win32DiskDriveInterfaceType String,
   win32DiskDrivePartitions Uint32,
   win32DiskDriveSectorsPerTrack Uint32,
   win32DiskDriveTotalCylinders String,
   win32DiskDriveTotalHeads Uint32,
   win32DiskDriveTotalSectors String,
   win32DiskDriveTotalTracks String,
   win32DiskDriveTracksPerCylinder Uint32,
   win32DiskDriveIndex Uint32,
   win32DiskDriveManufacturer String,
   win32DiskDriveMediaLoaded Boolean,
   win32DiskDriveMediaType String,
   win32DiskDriveModel String,
   win32DiskDriveSCSIBus Uint32,
   win32DiskDriveSCSILogicalUnit Uint16,
   win32DiskDriveSCSIPort Uint16,
   win32DiskDriveSCSITargetId Uint16,
   win32DiskDriveSize String,
   win32DiskDriveStatus String
}

win32DiskDriveKeyIndex OBJECT-TYPE
   SYNTAX         String
   ACCESS         read-write
   STATUS         mandatory
   DESCRIPTION    ""
   REFERENCE      "Win32_DiskDrive.KeyIndex"
::= { win32DiskDriveEntry 1 }

win32DiskDriveBytesPerSector OBJECT-TYPE
   SYNTAX         Uint32
   ACCESS         read-write
   STATUS         mandatory
   DESCRIPTION    "The BytesPerSector property indicates the number of bytes per sector for the physical disk drive.<P>Example: 512"
   REFERENCE      "Win32_DiskDrive.BytesPerSector"
::= { win32DiskDriveEntry 2 }

win32DiskDriveInterfaceType OBJECT-TYPE
   SYNTAX         String
   ACCESS         read-write
   STATUS         mandatory
   DESCRIPTION    "The InterfaceType property indicates the interface type of physical disk drive.<P>Example: IDE or SCSI"
   REFERENCE      "Win32_DiskDrive.InterfaceType"
::= { win32DiskDriveEntry 3 }

win32DiskDrivePartitions OBJECT-TYPE
   SYNTAX         Uint32
   ACCESS         read-write
   STATUS         mandatory
   DESCRIPTION    "The Partitions property indicates the number of partitions on this physical disk drive.<P>Example: 2"
   REFERENCE      "Win32_DiskDrive.Partitions"
::= { win32DiskDriveEntry 4 }

win32DiskDriveSectorsPerTrack OBJECT-TYPE
   SYNTAX         Uint32
   ACCESS         read-write
   STATUS         mandatory
   DESCRIPTION    "The SectorsPerTrack property indicates the number of sectors per track for this physical disk drive.<P>Example: 63"
   REFERENCE      "Win32_DiskDrive.SectorsPerTrack"
::= { win32DiskDriveEntry 5 }

win32DiskDriveTotalCylinders OBJECT-TYPE
   SYNTAX         String
   ACCESS         read-write
   STATUS         mandatory
   DESCRIPTION    "The TotalCylinders property indicates the total number of cylinders on the physical disk drive.<P>Example: 657"
   REFERENCE      "Win32_DiskDrive.TotalCylinders"
::= { win32DiskDriveEntry 6 }

win32DiskDriveTotalHeads OBJECT-TYPE
   SYNTAX         Uint32
   ACCESS         read-write
   STATUS         mandatory
   DESCRIPTION    "The TotalHeads property indicates the total number of heads on the disk drive."
   REFERENCE      "Win32_DiskDrive.TotalHeads"
::= { win32DiskDriveEntry 7 }

win32DiskDriveTotalSectors OBJECT-TYPE
   SYNTAX         String
   ACCESS         read-write
   STATUS         mandatory
   DESCRIPTION    "The TotalSectors property indicates the total number of sectors on the physical disk drive.<P>Example: 2649024"
   REFERENCE      "Win32_DiskDrive.TotalSectors"
::= { win32DiskDriveEntry 8 }

win32DiskDriveTotalTracks OBJECT-TYPE
   SYNTAX         String
   ACCESS         read-write
   STATUS         mandatory
   DESCRIPTION    "The TotalTracks property indicates the total number of tracks on the physical disk drive.<P>Example: 42048"
   REFERENCE      "Win32_DiskDrive.TotalTracks"
::= { win32DiskDriveEntry 9 }

win32DiskDriveTracksPerCylinder OBJECT-TYPE
   SYNTAX         Uint32
   ACCESS         read-write
   STATUS         mandatory
   DESCRIPTION    "The TrackPerCylinder property indicates the number of tracks per cylinder on the physical disk drive.<P>Example: 64"
   REFERENCE      "Win32_DiskDrive.TracksPerCylinder"
::= { win32DiskDriveEntry 10 }

win32DiskDriveIndex OBJECT-TYPE
   SYNTAX         Uint32
   ACCESS         read-write
   STATUS         mandatory
   DESCRIPTION    "The Index property indicates the index number of the disk drive.<P>Example: 1"
   REFERENCE      "Win32_DiskDrive.Index"
::= { win32DiskDriveEntry 11 }

win32DiskDriveManufacturer OBJECT-TYPE
   SYNTAX         String
   ACCESS         read-write
   STATUS         mandatory
   DESCRIPTION    "The Manufacturer property indicates the name of the disk drive manufacturer.<P>Example: Seagate"
   REFERENCE      "Win32_DiskDrive.Manufacturer"
::= { win32DiskDriveEntry 12 }

win32DiskDriveMediaLoaded OBJECT-TYPE
   SYNTAX         Boolean
   ACCESS         read-write
   STATUS         mandatory
   DESCRIPTION    "The MediaLoaded property determines whether the media for a removable disk drive is loaded.<P>Values: TRUE or FALSE. If TRUE, the media is loaded."
   REFERENCE      "Win32_DiskDrive.MediaLoaded"
::= { win32DiskDriveEntry 13 }

win32DiskDriveMediaType OBJECT-TYPE
   SYNTAX         String
   ACCESS         read-write
   STATUS         mandatory
   DESCRIPTION    "The MediaType property is the type of media used or accessed by this Device."
   REFERENCE      "Win32_DiskDrive.MediaType"
::= { win32DiskDriveEntry 14 }

win32DiskDriveModel OBJECT-TYPE
   SYNTAX         String
   ACCESS         read-write
   STATUS         mandatory
   DESCRIPTION    "The Model property indicates the manufacturer's model number of the disk drive.<P>Example: ST32171W"
   REFERENCE      "Win32_DiskDrive.Model"
::= { win32DiskDriveEntry 15 }

win32DiskDriveSCSIBus OBJECT-TYPE
   SYNTAX         Uint32
   ACCESS         read-write
   STATUS         mandatory
   DESCRIPTION    "The SCSIBus property indicates the SCSI bus number of the disk drive.<P>Example: 0"
   REFERENCE      "Win32_DiskDrive.SCSIBus"
::= { win32DiskDriveEntry 16 }

win32DiskDriveSCSILogicalUnit OBJECT-TYPE
   SYNTAX         Uint16
   ACCESS         read-write
   STATUS         mandatory
   DESCRIPTION    "The SCSILogicalUnit property indicates the SCSI logical unit number (LUN) of the disk drive.<P>Example: 0"
   REFERENCE      "Win32_DiskDrive.SCSILogicalUnit"
::= { win32DiskDriveEntry 17 }

win32DiskDriveSCSIPort OBJECT-TYPE
   SYNTAX         Uint16
   ACCESS         read-write
   STATUS         mandatory
   DESCRIPTION    "The SCSIPort property indicates the SCSI port number of the disk drive.<P>Example: 0"
   REFERENCE      "Win32_DiskDrive.SCSIPort"
::= { win32DiskDriveEntry 18 }

win32DiskDriveSCSITargetId OBJECT-TYPE
   SYNTAX         Uint16
   ACCESS         read-write
   STATUS         mandatory
   DESCRIPTION    "The SCSITargetId property indicates the SCSI ID number of the disk drive.<P>Example: 0"
   REFERENCE      "Win32_DiskDrive.SCSITargetId"
::= { win32DiskDriveEntry 19 }

win32DiskDriveSize OBJECT-TYPE
   SYNTAX         String
   ACCESS         read-write
   STATUS         mandatory
   DESCRIPTION    "The Size property indicates the size (in bytes) of the disk drive."
   REFERENCE      "Win32_DiskDrive.Size"
::= { win32DiskDriveEntry 20 }

win32DiskDriveStatus OBJECT-TYPE
   SYNTAX         String
   ACCESS         read-write
   STATUS         mandatory
   DESCRIPTION    "The Status property is a string indicating the current status of the object. Various operational and non-operational statuses can be defined. Operational statuses are OK, Degraded and Pred Fail. Pred Fail indicates that an element may be functioning properly but predicting a failure in the near future. An example is a SMART-enabled hard drive. Non-operational statuses can also be specified. These are Error, Starting, Stopping and Service. The latter, Service, could apply during mirror-resilvering of a disk, reload of a user permissions list, or other administrative work. Not all such work is on-line, yet the managed element is neither OK nor in one of the other states."
   REFERENCE      "Win32_DiskDrive.Status"
::= { win32DiskDriveEntry 21 }

win32CDROMDriveTable OBJECT-TYPE
   SYNTAX         SEQUENCE OF Win32CDROMDriveEntry
   ACCESS         not-accessible
   STATUS         mandatory
   DESCRIPTION    "The Win32_CDROMDrive class represents a CD-ROM drive on a Win32 system."
   REFERENCE      "Win32_CDROMDrive"
::= { win32WMI 40 }

win32CDROMDriveEntry OBJECT-TYPE
   SYNTAX         Win32CDROMDriveEntry
   ACCESS         not-accessible
   STATUS         mandatory
   DESCRIPTION    ""
   INDEX          { win32CDROMDriveKeyIndex }
::= { win32CDROMDriveTable 1 }

Win32CDROMDriveEntry ::= SEQUENCE
{
   win32CDROMDriveKeyIndex String,
   win32CDROMDriveDrive String,
   win32CDROMDriveFileSystemFlags Uint16,
   win32CDROMDriveId String,
   win32CDROMDriveManufacturer String,
   win32CDROMDriveMaximumComponentLength Uint32,
   win32CDROMDriveMediaType String,
   win32CDROMDriveRevisionLevel String,
   win32CDROMDriveSCSITargetId Uint16,
   win32CDROMDriveVolumeName String,
   win32CDROMDriveVolumeSerialNumber String,
   win32CDROMDriveTransferRate Real64,
   win32CDROMDriveDriveIntegrity Boolean,
   win32CDROMDriveMediaLoaded Boolean,
   win32CDROMDriveStatus String
}

win32CDROMDriveKeyIndex OBJECT-TYPE
   SYNTAX         String
   ACCESS         read-write
   STATUS         mandatory
   DESCRIPTION    ""
   REFERENCE      "Win32_CDROMDrive.KeyIndex"
::= { win32CDROMDriveEntry 1 }

win32CDROMDriveDrive OBJECT-TYPE
   SYNTAX         String
   ACCESS         read-write
   STATUS         mandatory
   DESCRIPTION    "The Drive property indicates the drive letter of the CD ROM drive.<P>Example: d:"
   REFERENCE      "Win32_CDROMDrive.Drive"
::= { win32CDROMDriveEntry 2 }

win32CDROMDriveFileSystemFlags OBJECT-TYPE
   SYNTAX         Uint16
   ACCESS         read-write
   STATUS         mandatory
   DESCRIPTION    "The FileSystemFlags property indicates the file system flags of the Win32 CD ROM drive.<P>Example: 0"
   REFERENCE      "Win32_CDROMDrive.FileSystemFlags"
::= { win32CDROMDriveEntry 3 }

win32CDROMDriveId OBJECT-TYPE
   SYNTAX         String
   ACCESS         read-write
   STATUS         mandatory
   DESCRIPTION    "The Id property indicates the manufacturer's identifying name of the Win32 CD ROM drive.<P>Example: PLEXTOR CD-ROM PX-12CS  1.01"
   REFERENCE      "Win32_CDROMDrive.Id"
::= { win32CDROMDriveEntry 4 }

win32CDROMDriveManufacturer OBJECT-TYPE
   SYNTAX         String
   ACCESS         read-write
   STATUS         mandatory
   DESCRIPTION    "The Manufacturer property indicates the manufacturer of the Win32 CD ROM drive.<P>Example: PLEXTOR"
   REFERENCE      "Win32_CDROMDrive.Manufacturer"
::= { win32CDROMDriveEntry 5 }

win32CDROMDriveMaximumComponentLength OBJECT-TYPE
   SYNTAX         Uint32
   ACCESS         read-write
   STATUS         mandatory
   DESCRIPTION    "The MaximumComponentLength property indicates the maximum component length of the Win32 CD ROM drive.<P>Example: 0"
   REFERENCE      "Win32_CDROMDrive.MaximumComponentLength"
::= { win32CDROMDriveEntry 6 }

win32CDROMDriveMediaType OBJECT-TYPE
   SYNTAX         String
   ACCESS         read-write
   STATUS         mandatory
   DESCRIPTION    "The MediaType property is the type of media used or accessed by this Device."
   REFERENCE      "Win32_CDROMDrive.MediaType"
::= { win32CDROMDriveEntry 7 }

win32CDROMDriveRevisionLevel OBJECT-TYPE
   SYNTAX         String
   ACCESS         read-write
   STATUS         mandatory
   DESCRIPTION    "The RevisionLevel property indicates the firmware revision level of the Win32 CD ROM drive."
   REFERENCE      "Win32_CDROMDrive.RevisionLevel"
::= { win32CDROMDriveEntry 8 }

win32CDROMDriveSCSITargetId OBJECT-TYPE
   SYNTAX         Uint16
   ACCESS         read-write
   STATUS         mandatory
   DESCRIPTION    "The SCSITargetId property indicates the SCSI ID number of the Win32 CD ROM drive.<P>Example: 0"
   REFERENCE      "Win32_CDROMDrive.SCSITargetId"
::= { win32CDROMDriveEntry 9 }

win32CDROMDriveVolumeName OBJECT-TYPE
   SYNTAX         String
   ACCESS         read-write
   STATUS         mandatory
   DESCRIPTION    "The VolumeName property indicates the volume name of the Win32 CD ROM drive.<P>Example: 0"
   REFERENCE      "Win32_CDROMDrive.VolumeName"
::= { win32CDROMDriveEntry 10 }

win32CDROMDriveVolumeSerialNumber OBJECT-TYPE
   SYNTAX         String
   ACCESS         read-write
   STATUS         mandatory
   DESCRIPTION    "The VolumeSerialNumber property indicates the volume serial number of the Win32 CD ROM drive.<P>Example: 0"
   REFERENCE      "Win32_CDROMDrive.VolumeSerialNumber"
::= { win32CDROMDriveEntry 11 }

win32CDROMDriveTransferRate OBJECT-TYPE
   SYNTAX         Real64
   ACCESS         read-write
   STATUS         mandatory
   DESCRIPTION    "The TransferRate property returns the CD drive's transfer rate in kilobytes per second (KBytes/sec).  A NULL value indicates that the rate could not be determined."
   REFERENCE      "Win32_CDROMDrive.TransferRate"
::= { win32CDROMDriveEntry 12 }

win32CDROMDriveDriveIntegrity OBJECT-TYPE
   SYNTAX         Boolean
   ACCESS         read-write
   STATUS         mandatory
   DESCRIPTION    "The DriveIntegrity property indicates whether files can be accurately read from the CD device."
   REFERENCE      "Win32_CDROMDrive.DriveIntegrity"
::= { win32CDROMDriveEntry 13 }

win32CDROMDriveMediaLoaded OBJECT-TYPE
   SYNTAX         Boolean
   ACCESS         read-write
   STATUS         mandatory
   DESCRIPTION    "The MediaLoaded property indicates whether a CD ROM is loaded. <P>Values: TRUE or FALSE. If TRUE, the media is loaded."
   REFERENCE      "Win32_CDROMDrive.MediaLoaded"
::= { win32CDROMDriveEntry 14 }

win32CDROMDriveStatus OBJECT-TYPE
   SYNTAX         String
   ACCESS         read-write
   STATUS         mandatory
   DESCRIPTION    "The Status property is a string indicating the current status of the object. Various operational and non-operational statuses can be defined. Operational statuses are OK, Degraded and Pred Fail. Pred Fail indicates that an element may be functioning properly but predicting a failure in the near future. An example is a SMART-enabled hard drive. Non-operational statuses can also be specified. These are Error, Starting, Stopping and Service. The latter, Service, could apply during mirror-resilvering of a disk, reload of a user permissions list, or other administrative work. Not all such work is on-line, yet the managed element is neither OK nor in one of the other states."
   REFERENCE      "Win32_CDROMDrive.Status"
::= { win32CDROMDriveEntry 15 }

win32PointingDeviceTable OBJECT-TYPE
   SYNTAX         SEQUENCE OF Win32PointingDeviceEntry
   ACCESS         not-accessible
   STATUS         mandatory
   DESCRIPTION    "The Win32_PointingDevice class represents a device used to point to regions on the display of a Win32 system. Any device used to point to regions on the display on a Win32 system is a member of this class.<P>Example: A mouse, stylus, touch pad, or tablet"
   REFERENCE      "Win32_PointingDevice"
::= { win32WMI 50 }

win32PointingDeviceEntry OBJECT-TYPE
   SYNTAX         Win32PointingDeviceEntry
   ACCESS         not-accessible
   STATUS         mandatory
   DESCRIPTION    ""
   INDEX          { win32PointingDeviceKeyIndex }
::= { win32PointingDeviceTable 1 }

Win32PointingDeviceEntry ::= SEQUENCE
{
   win32PointingDeviceKeyIndex String,
   win32PointingDeviceHardwareType String,
   win32PointingDeviceInfFileName String,
   win32PointingDeviceInfSection String,
   win32PointingDeviceSampleRate Uint32,
   win32PointingDeviceSynch Uint32,
   win32PointingDeviceDoubleSpeedThreshold Uint32,
   win32PointingDeviceQuadSpeedThreshold Uint32,
   win32PointingDeviceStatus String
}

win32PointingDeviceKeyIndex OBJECT-TYPE
   SYNTAX         String
   ACCESS         read-write
   STATUS         mandatory
   DESCRIPTION    ""
   REFERENCE      "Win32_PointingDevice.KeyIndex"
::= { win32PointingDeviceEntry 1 }

win32PointingDeviceHardwareType OBJECT-TYPE
   SYNTAX         String
   ACCESS         read-write
   STATUS         mandatory
   DESCRIPTION    "The HardwareType property indicates the hardware type of Win32 pointing device.<P>Example: MICROSOFT PS2 MOUSE"
   REFERENCE      "Win32_PointingDevice.HardwareType"
::= { win32PointingDeviceEntry 2 }

win32PointingDeviceInfFileName OBJECT-TYPE
   SYNTAX         String
   ACCESS         read-write
   STATUS         mandatory
   DESCRIPTION    "The InfFileName property indicates the name of the INF file for the Win32 pointing device.<P>Example: ab.inf"
   REFERENCE      "Win32_PointingDevice.InfFileName"
::= { win32PointingDeviceEntry 3 }

win32PointingDeviceInfSection OBJECT-TYPE
   SYNTAX         String
   ACCESS         read-write
   STATUS         mandatory
   DESCRIPTION    "The InfSection property indicates the section of the INF file that holds configuration information for the Win32 pointing device."
   REFERENCE      "Win32_PointingDevice.InfSection"
::= { win32PointingDeviceEntry 4 }

win32PointingDeviceSampleRate OBJECT-TYPE
   SYNTAX         Uint32
   ACCESS         read-write
   STATUS         mandatory
   DESCRIPTION    "The SampleRate property indicates the sample rate of the Win32 pointing device."
   REFERENCE      "Win32_PointingDevice.SampleRate"
::= { win32PointingDeviceEntry 5 }

win32PointingDeviceSynch OBJECT-TYPE
   SYNTAX         Uint32
   ACCESS         read-write
   STATUS         mandatory
   DESCRIPTION    ""
   REFERENCE      "Win32_PointingDevice.Synch"
::= { win32PointingDeviceEntry 6 }

win32PointingDeviceDoubleSpeedThreshold OBJECT-TYPE
   SYNTAX         Uint32
   ACCESS         read-write
   STATUS         mandatory
   DESCRIPTION    ""
   REFERENCE      "Win32_PointingDevice.DoubleSpeedThreshold"
::= { win32PointingDeviceEntry 7 }

win32PointingDeviceQuadSpeedThreshold OBJECT-TYPE
   SYNTAX         Uint32
   ACCESS         read-write
   STATUS         mandatory
   DESCRIPTION    ""
   REFERENCE      "Win32_PointingDevice.QuadSpeedThreshold"
::= { win32PointingDeviceEntry 8 }

win32PointingDeviceStatus OBJECT-TYPE
   SYNTAX         String
   ACCESS         read-write
   STATUS         mandatory
   DESCRIPTION    "The Status property is a string indicating the current status of the object. Various operational and non-operational statuses can be defined. Operational statuses are OK, Degraded and Pred Fail. Pred Fail indicates that an element may be functioning properly but predicting a failure in the near future. An example is a SMART-enabled hard drive. Non-operational statuses can also be specified. These are Error, Starting, Stopping and Service. The latter, Service, could apply during mirror-resilvering of a disk, reload of a user permissions list, or other administrative work. Not all such work is on-line, yet the managed element is neither OK nor in one of the other states."
   REFERENCE      "Win32_PointingDevice.Status"
::= { win32PointingDeviceEntry 9 }

win32LogicalDiskTable OBJECT-TYPE
   SYNTAX         SEQUENCE OF Win32LogicalDiskEntry
   ACCESS         not-accessible
   STATUS         mandatory
   DESCRIPTION    "The Win32_LogicalDisk class represents a logical disk on a Win32 system."
   REFERENCE      "Win32_LogicalDisk"
::= { win32WMI 70 }

win32LogicalDiskEntry OBJECT-TYPE
   SYNTAX         Win32LogicalDiskEntry
   ACCESS         not-accessible
   STATUS         mandatory
   DESCRIPTION    ""
   INDEX          { win32LogicalDiskKeyIndex }
::= { win32LogicalDiskTable 1 }

Win32LogicalDiskEntry ::= SEQUENCE
{
   win32LogicalDiskKeyIndex String,
   win32LogicalDiskCompressed Boolean,
   win32LogicalDiskDriveType Uint32,
   win32LogicalDiskFileSystem String,
   win32LogicalDiskFreeSpace String,
   win32LogicalDiskMaximumComponentLength Uint32,
   win32LogicalDiskProviderName String,
   win32LogicalDiskSize String,
   win32LogicalDiskSupportsFileBasedCompression Boolean,
   win32LogicalDiskVolumeName String,
   win32LogicalDiskVolumeSerialNumber String,
   win32LogicalDiskMediaType Uint32,
   win32LogicalDiskStatus String
}

win32LogicalDiskKeyIndex OBJECT-TYPE
   SYNTAX         String
   ACCESS         read-write
   STATUS         mandatory
   DESCRIPTION    ""
   REFERENCE      "Win32_LogicalDisk.KeyIndex"
::= { win32LogicalDiskEntry 1 }

win32LogicalDiskCompressed OBJECT-TYPE
   SYNTAX         Boolean
   ACCESS         read-write
   STATUS         mandatory
   DESCRIPTION    "The Compressed property indicates whether the logical volume exists as a single compressed entity, such as a DoubleSpace volume.  If file based compression is supported (such as on NTFS), this property will be FALSE."
   REFERENCE      "Win32_LogicalDisk.Compressed"
::= { win32LogicalDiskEntry 2 }

win32LogicalDiskDriveType OBJECT-TYPE
   SYNTAX         Uint32
   ACCESS         read-write
   STATUS         mandatory
   DESCRIPTION    "The DriveType property contains a numeric representation of the type of disk drive represented by this logical disk.<P>Example: A CDRom would return 5"
   REFERENCE      "Win32_LogicalDisk.DriveType"
::= { win32LogicalDiskEntry 3 }

win32LogicalDiskFileSystem OBJECT-TYPE
   SYNTAX         String
   ACCESS         read-write
   STATUS         mandatory
   DESCRIPTION    "The FileSystem property indicates the file system on the logical disk.<P>Example: NTFS"
   REFERENCE      "Win32_LogicalDisk.FileSystem"
::= { win32LogicalDiskEntry 4 }

win32LogicalDiskFreeSpace OBJECT-TYPE
   SYNTAX         String
   ACCESS         read-write
   STATUS         mandatory
   DESCRIPTION    ""
   REFERENCE      "Win32_LogicalDisk.FreeSpace"
::= { win32LogicalDiskEntry 5 }

win32LogicalDiskMaximumComponentLength OBJECT-TYPE
   SYNTAX         Uint32
   ACCESS         read-write
   STATUS         mandatory
   DESCRIPTION    "The MaximumComponentLength property indicates the maximum component length of the logical drive."
   REFERENCE      "Win32_LogicalDisk.MaximumComponentLength"
::= { win32LogicalDiskEntry 6 }

win32LogicalDiskProviderName OBJECT-TYPE
   SYNTAX         String
   ACCESS         read-write
   STATUS         mandatory
   DESCRIPTION    "The ProviderName property indicates the provider name of the logical disk."
   REFERENCE      "Win32_LogicalDisk.ProviderName"
::= { win32LogicalDiskEntry 7 }

win32LogicalDiskSize OBJECT-TYPE
   SYNTAX         String
   ACCESS         read-write
   STATUS         mandatory
   DESCRIPTION    ""
   REFERENCE      "Win32_LogicalDisk.Size"
::= { win32LogicalDiskEntry 8 }

win32LogicalDiskSupportsFileBasedCompression OBJECT-TYPE
   SYNTAX         Boolean
   ACCESS         read-write
   STATUS         mandatory
   DESCRIPTION    "The SupportsFileBasedCompression property indicates whether the logical disk partition supports file based compression, such as is the case with NTFS. If this property is TRUE, the Compressed property will be FALSE, but not necessarily vice versa.<P>Values: TRUE or FALSE. If TRUE, the logical disk supports file based compression."
   REFERENCE      "Win32_LogicalDisk.SupportsFileBasedCompression"
::= { win32LogicalDiskEntry 9 }

win32LogicalDiskVolumeName OBJECT-TYPE
   SYNTAX         String
   ACCESS         read-write
   STATUS         mandatory
   DESCRIPTION    "The VolumeName property indicates the volume name on the logical disk.<P>Constraints: Maximum 32 characters"
   REFERENCE      "Win32_LogicalDisk.VolumeName"
::= { win32LogicalDiskEntry 10 }

win32LogicalDiskVolumeSerialNumber OBJECT-TYPE
   SYNTAX         String
   ACCESS         read-write
   STATUS         mandatory
   DESCRIPTION    "The VolumeSerialNumber property indicates the volume serial number of the logical disk.<P>Constraints: Maximum 11 characters"
   REFERENCE      "Win32_LogicalDisk.VolumeSerialNumber"
::= { win32LogicalDiskEntry 11 }

win32LogicalDiskMediaType OBJECT-TYPE
   SYNTAX         Uint32
   ACCESS         read-write
   STATUS         mandatory
   DESCRIPTION    "The MediaType property indicates the type of media currently present in the logical drive. This value will be one of the the values of the MEDIA_TYPE enumeration defined in winioctl.h.<P><B>Note:</B> The value may not be exact for removable drives if currently there is no media in the drive."
   REFERENCE      "Win32_LogicalDisk.MediaType"
::= { win32LogicalDiskEntry 12 }

win32LogicalDiskStatus OBJECT-TYPE
   SYNTAX         String
   ACCESS         read-write
   STATUS         mandatory
   DESCRIPTION    "The Status property is a string indicating the current status of the object. Various operational and non-operational statuses can be defined. Operational statuses are OK, Degraded and Pred Fail. Pred Fail indicates that an element may be functioning properly but predicting a failure in the near future. An example is a SMART-enabled hard drive. Non-operational statuses can also be specified. These are Error, Starting, Stopping and Service. The latter, Service, could apply during mirror-resilvering of a disk, reload of a user permissions list, or other administrative work. Not all such work is on-line, yet the managed element is neither OK nor in one of the other states."
   REFERENCE      "Win32_LogicalDisk.Status"
::= { win32LogicalDiskEntry 13 }

win32DiskPartitionTable OBJECT-TYPE
   SYNTAX         SEQUENCE OF Win32DiskPartitionEntry
   ACCESS         not-accessible
   STATUS         mandatory
   DESCRIPTION    "The Win32_DiskPartition class represents an area of a physical disk on a Win32 system.<P>Example: Disk #0, Partition #1"
   REFERENCE      "Win32_DiskPartition"
::= { win32WMI 80 }

win32DiskPartitionEntry OBJECT-TYPE
   SYNTAX         Win32DiskPartitionEntry
   ACCESS         not-accessible
   STATUS         mandatory
   DESCRIPTION    ""
   INDEX          { win32DiskPartitionKeyIndex }
::= { win32DiskPartitionTable 1 }

Win32DiskPartitionEntry ::= SEQUENCE
{
   win32DiskPartitionKeyIndex String,
   win32DiskPartitionBootPartition Boolean,
   win32DiskPartitionDiskIndex Uint32,
   win32DiskPartitionHiddenSectors Uint32,
   win32DiskPartitionIndex Uint32,
   win32DiskPartitionRewritePartition Boolean,
   win32DiskPartitionSize String,
   win32DiskPartitionStartingOffset String,
   win32DiskPartitionType String,
   win32DiskPartitionStatus String
}

win32DiskPartitionKeyIndex OBJECT-TYPE
   SYNTAX         String
   ACCESS         read-write
   STATUS         mandatory
   DESCRIPTION    ""
   REFERENCE      "Win32_DiskPartition.KeyIndex"
::= { win32DiskPartitionEntry 1 }

win32DiskPartitionBootPartition OBJECT-TYPE
   SYNTAX         Boolean
   ACCESS         read-write
   STATUS         mandatory
   DESCRIPTION    "The BootPartition property determines whether the partition is bootable.<P>Values: TRUE or FALSE. If TRUE, the partition is bootable."
   REFERENCE      "Win32_DiskPartition.BootPartition"
::= { win32DiskPartitionEntry 2 }

win32DiskPartitionDiskIndex OBJECT-TYPE
   SYNTAX         Uint32
   ACCESS         read-write
   STATUS         mandatory
   DESCRIPTION    "The DiskIndex property indicates the disk index number of the partition.<P>Example: 0"
   REFERENCE      "Win32_DiskPartition.DiskIndex"
::= { win32DiskPartitionEntry 3 }

win32DiskPartitionHiddenSectors OBJECT-TYPE
   SYNTAX         Uint32
   ACCESS         read-write
   STATUS         mandatory
   DESCRIPTION    "The HiddenSectors property indicates the number of hidden sectors in the partition.<P>Example: 63"
   REFERENCE      "Win32_DiskPartition.HiddenSectors"
::= { win32DiskPartitionEntry 4 }

win32DiskPartitionIndex OBJECT-TYPE
   SYNTAX         Uint32
   ACCESS         read-write
   STATUS         mandatory
   DESCRIPTION    "The Index property indicates the index number of the partition.<P>Example: 1"
   REFERENCE      "Win32_DiskPartition.Index"
::= { win32DiskPartitionEntry 5 }

win32DiskPartitionRewritePartition OBJECT-TYPE
   SYNTAX         Boolean
   ACCESS         read-write
   STATUS         mandatory
   DESCRIPTION    "The RewritePartition property determines whether the partition is rewriteable.<P>Values: TRUE or FALSE. If TRUE, the partition is rewriteable."
   REFERENCE      "Win32_DiskPartition.RewritePartition"
::= { win32DiskPartitionEntry 6 }

win32DiskPartitionSize OBJECT-TYPE
   SYNTAX         String
   ACCESS         read-write
   STATUS         mandatory
   DESCRIPTION    "The Size property indicates the total size (in bytes) of the partition.<P>Example: 1059045376"
   REFERENCE      "Win32_DiskPartition.Size"
::= { win32DiskPartitionEntry 7 }

win32DiskPartitionStartingOffset OBJECT-TYPE
   SYNTAX         String
   ACCESS         read-write
   STATUS         mandatory
   DESCRIPTION    "The StartingOffset property indicates the starting offset (in bytes) of the partition.<P>Example: 32256"
   REFERENCE      "Win32_DiskPartition.StartingOffset"
::= { win32DiskPartitionEntry 8 }

win32DiskPartitionType OBJECT-TYPE
   SYNTAX         String
   ACCESS         read-write
   STATUS         mandatory
   DESCRIPTION    "The Type property indicates the type of the partition."
   REFERENCE      "Win32_DiskPartition.Type"
::= { win32DiskPartitionEntry 9 }

win32DiskPartitionStatus OBJECT-TYPE
   SYNTAX         String
   ACCESS         read-write
   STATUS         mandatory
   DESCRIPTION    "The Status property is a string indicating the current status of the object. Various operational and non-operational statuses can be defined. Operational statuses are OK, Degraded and Pred Fail. Pred Fail indicates that an element may be functioning properly but predicting a failure in the near future. An example is a SMART-enabled hard drive. Non-operational statuses can also be specified. These are Error, Starting, Stopping and Service. The latter, Service, could apply during mirror-resilvering of a disk, reload of a user permissions list, or other administrative work. Not all such work is on-line, yet the managed element is neither OK nor in one of the other states."
   REFERENCE      "Win32_DiskPartition.Status"
::= { win32DiskPartitionEntry 10 }

win32BatteryTable OBJECT-TYPE
   SYNTAX         SEQUENCE OF Win32BatteryEntry
   ACCESS         not-accessible
   STATUS         mandatory
   DESCRIPTION    "The Win32_Battery class represents a battery connected to the system.  This could be either a UPS, or a laptop battery.  <P>Example: Uninterruptible Power Supply"
   REFERENCE      "Win32_Battery"
::= { win32WMI 90 }

win32BatteryEntry OBJECT-TYPE
   SYNTAX         Win32BatteryEntry
   ACCESS         not-accessible
   STATUS         mandatory
   DESCRIPTION    ""
   INDEX          { win32BatteryKeyIndex }
::= { win32BatteryTable 1 }

Win32BatteryEntry ::= SEQUENCE
{
   win32BatteryKeyIndex String,
   win32BatteryExpectedBatteryLife Uint16,
   win32BatteryBatteryRechargeTime Uint16,
   win32BatteryBatteryStatus String
}

win32BatteryKeyIndex OBJECT-TYPE
   SYNTAX         String
   ACCESS         read-write
   STATUS         mandatory
   DESCRIPTION    ""
   REFERENCE      "Win32_Battery.KeyIndex"
::= { win32BatteryEntry 1 }

win32BatteryExpectedBatteryLife OBJECT-TYPE
   SYNTAX         Uint16
   ACCESS         read-write
   STATUS         mandatory
   DESCRIPTION    "The ExpectedBatteryLife property indicates the time in minutes of the expected life of the fully charged battery."
   REFERENCE      "Win32_Battery.ExpectedBatteryLife"
::= { win32BatteryEntry 2 }

win32BatteryBatteryRechargeTime OBJECT-TYPE
   SYNTAX         Uint16
   ACCESS         read-write
   STATUS         mandatory
   DESCRIPTION    "The BatteryRechargeTime property indicates the time for recharging the battery."
   REFERENCE      "Win32_Battery.BatteryRechargeTime"
::= { win32BatteryEntry 3 }

win32BatteryBatteryStatus OBJECT-TYPE
   SYNTAX         String
   ACCESS         read-write
   STATUS         mandatory
   DESCRIPTION    "The Status property is a string indicating the current status of the object. Various operational and non-operational statuses can be defined. Operational statuses are OK, Degraded and Pred Fail. Pred Fail indicates that an element may be functioning properly but predicting a failure in the near future. An example is a SMART-enabled hard drive. Non-operational statuses can also be specified. These are Error, Starting, Stopping and Service. The latter, Service, could apply during mirror-resilvering of a disk, reload of a user permissions list, or other administrative work. Not all such work is on-line, yet the managed element is neither OK nor in one of the other states."
   REFERENCE      "Win32_Battery.Status"
::= { win32BatteryEntry 4 }

win32MotherboardDeviceTable OBJECT-TYPE
   SYNTAX         SEQUENCE OF Win32MotherboardDeviceEntry
   ACCESS         not-accessible
   STATUS         mandatory
   DESCRIPTION    "The Win32_MotherboardDevice class represents a device that contains the central components of the Win32 system.<P>Example: A single piece of hardware containing a processor, bus, memory, and basic system interfaces"
   REFERENCE      "Win32_MotherboardDevice"
::= { win32WMI 100 }

win32MotherboardDeviceEntry OBJECT-TYPE
   SYNTAX         Win32MotherboardDeviceEntry
   ACCESS         not-accessible
   STATUS         mandatory
   DESCRIPTION    ""
   INDEX          { win32MotherboardDeviceKeyIndex }
::= { win32MotherboardDeviceTable 1 }

Win32MotherboardDeviceEntry ::= SEQUENCE
{
   win32MotherboardDeviceKeyIndex String,
   win32MotherboardDevicePrimaryBusType String,
   win32MotherboardDeviceRevisionNumber String,
   win32MotherboardDeviceSecondaryBusType String,
   win32MotherboardDeviceStatus String
}

win32MotherboardDeviceKeyIndex OBJECT-TYPE
   SYNTAX         String
   ACCESS         read-write
   STATUS         mandatory
   DESCRIPTION    ""
   REFERENCE      "Win32_MotherboardDevice.KeyIndex"
::= { win32MotherboardDeviceEntry 1 }

win32MotherboardDevicePrimaryBusType OBJECT-TYPE
   SYNTAX         String
   ACCESS         read-write
   STATUS         mandatory
   DESCRIPTION    "The PrimaryBusType property indicates the primary bus type of the Win32 motherboard.<P>Example: PCI"
   REFERENCE      "Win32_MotherboardDevice.PrimaryBusType"
::= { win32MotherboardDeviceEntry 2 }

win32MotherboardDeviceRevisionNumber OBJECT-TYPE
   SYNTAX         String
   ACCESS         read-write
   STATUS         mandatory
   DESCRIPTION    "The RevisionNumber property indicates the revision number of the Win32 motherboard.<P>Example: 00"
   REFERENCE      "Win32_MotherboardDevice.RevisionNumber"
::= { win32MotherboardDeviceEntry 3 }

win32MotherboardDeviceSecondaryBusType OBJECT-TYPE
   SYNTAX         String
   ACCESS         read-write
   STATUS         mandatory
   DESCRIPTION    "The SecondaryBusType property indicates the secondary bus type of the Win32 motherboard.<P>Example: ISA"
   REFERENCE      "Win32_MotherboardDevice.SecondaryBusType"
::= { win32MotherboardDeviceEntry 4 }

win32MotherboardDeviceStatus OBJECT-TYPE
   SYNTAX         String
   ACCESS         read-write
   STATUS         mandatory
   DESCRIPTION    "The Status property is a string indicating the current status of the object. Various operational and non-operational statuses can be defined. Operational statuses are OK, Degraded and Pred Fail. Pred Fail indicates that an element may be functioning properly but predicting a failure in the near future. An example is a SMART-enabled hard drive. Non-operational statuses can also be specified. These are Error, Starting, Stopping and Service. The latter, Service, could apply during mirror-resilvering of a disk, reload of a user permissions list, or other administrative work. Not all such work is on-line, yet the managed element is neither OK nor in one of the other states."
   REFERENCE      "Win32_MotherboardDevice.Status"
::= { win32MotherboardDeviceEntry 5 }

win32ProcessorTable OBJECT-TYPE
   SYNTAX         SEQUENCE OF Win32ProcessorEntry
   ACCESS         not-accessible
   STATUS         mandatory
   DESCRIPTION    "The Win32_Processor class represents a device that is capable of interpreting a sequence of machine instructions on a Win32 system.<P>Example: Intel 486/66"
   REFERENCE      "Win32_Processor"
::= { win32WMI 110 }

win32ProcessorEntry OBJECT-TYPE
   SYNTAX         Win32ProcessorEntry
   ACCESS         not-accessible
   STATUS         mandatory
   DESCRIPTION    ""
   INDEX          { win32ProcessorKeyIndex }
::= { win32ProcessorTable 1 }

Win32ProcessorEntry ::= SEQUENCE
{
   win32ProcessorKeyIndex String,
   win32ProcessorVersion String,
   win32ProcessorManufacturer String,
   win32ProcessorL2CacheSize Uint32,
   win32ProcessorL2CacheSpeed Uint32,
   win32ProcessorArchitecture Uint16,
   win32ProcessorLevel Uint16,
   win32ProcessorRevision Uint16,
   win32ProcessorStatus String
}

win32ProcessorKeyIndex OBJECT-TYPE
   SYNTAX         String
   ACCESS         read-write
   STATUS         mandatory
   DESCRIPTION    ""
   REFERENCE      "Win32_Processor.KeyIndex"
::= { win32ProcessorEntry 1 }

win32ProcessorVersion OBJECT-TYPE
   SYNTAX         String
   ACCESS         read-write
   STATUS         mandatory
   DESCRIPTION    "The Version property indicates the version of the processor.<P>Example: Model 2, Stepping 12"
   REFERENCE      "Win32_Processor.Version"
::= { win32ProcessorEntry 2 }

win32ProcessorManufacturer OBJECT-TYPE
   SYNTAX         String
   ACCESS         read-write
   STATUS         mandatory
   DESCRIPTION    "The Manufacturer property indicates the name of the organization responsible for producing the processor.<P>Example: GenuineSilicon"
   REFERENCE      "Win32_Processor.Manufacturer"
::= { win32ProcessorEntry 3 }

win32ProcessorL2CacheSize OBJECT-TYPE
   SYNTAX         Uint32
   ACCESS         read-write
   STATUS         mandatory
   DESCRIPTION    "The L2CacheSize property indicates the size in kilobytes of the  processor's L2 cache."
   REFERENCE      "Win32_Processor.L2CacheSize"
::= { win32ProcessorEntry 4 }

win32ProcessorL2CacheSpeed OBJECT-TYPE
   SYNTAX         Uint32
   ACCESS         read-write
   STATUS         mandatory
   DESCRIPTION    "The L2CacheSpeed property indicates the speed in MHz of the  processor's L2 cache."
   REFERENCE      "Win32_Processor.L2CacheSpeed"
::= { win32ProcessorEntry 5 }

win32ProcessorArchitecture OBJECT-TYPE
   SYNTAX         Uint16
   ACCESS         read-write
   STATUS         mandatory
   DESCRIPTION    "The Architecture property indicates the instruction set architecture of the processor. Values are: 0=\, 1=\, 2=\, 3=\"
   REFERENCE      "Win32_Processor.Architecture"
::= { win32ProcessorEntry 6 }

win32ProcessorLevel OBJECT-TYPE
   SYNTAX         Uint16
   ACCESS         read-write
   STATUS         mandatory
   DESCRIPTION    "The Level property specifies the system's architecture-dependent processor level."
   REFERENCE      "Win32_Processor.Level"
::= { win32ProcessorEntry 7 }

win32ProcessorRevision OBJECT-TYPE
   SYNTAX         Uint16
   ACCESS         read-write
   STATUS         mandatory
   DESCRIPTION    "The Revision property specifies the system's architecture-dependent revision level."
   REFERENCE      "Win32_Processor.Revision"
::= { win32ProcessorEntry 8 }

win32ProcessorStatus OBJECT-TYPE
   SYNTAX         String
   ACCESS         read-write
   STATUS         mandatory
   DESCRIPTION    "The Status property is a string indicating the current status of the object. Various operational and non-operational statuses can be defined. Operational statuses are OK, Degraded and Pred Fail. Pred Fail indicates that an element may be functioning properly but predicting a failure in the near future. An example is a SMART-enabled hard drive. Non-operational statuses can also be specified. These are Error, Starting, Stopping and Service. The latter, Service, could apply during mirror-resilvering of a disk, reload of a user permissions list, or other administrative work. Not all such work is on-line, yet the managed element is neither OK nor in one of the other states."
   REFERENCE      "Win32_Processor.Status"
::= { win32ProcessorEntry 9 }

win32PrinterTable OBJECT-TYPE
   SYNTAX         SEQUENCE OF Win32PrinterEntry
   ACCESS         not-accessible
   STATUS         mandatory
   DESCRIPTION    "The Win32_Printer class represents a device connected to a Win32 system that is capable of reproducing a visual image on a medium."
   REFERENCE      "Win32_Printer"
::= { win32WMI 120 }

win32PrinterEntry OBJECT-TYPE
   SYNTAX         Win32PrinterEntry
   ACCESS         not-accessible
   STATUS         mandatory
   DESCRIPTION    ""
   INDEX          { win32PrinterKeyIndex }
::= { win32PrinterTable 1 }

Win32PrinterEntry ::= SEQUENCE
{
   win32PrinterKeyIndex String,
   win32PrinterAttributes Uint32,
   win32PrinterDriverName String,
   win32PrinterLocation String,
   win32PrinterPrinterPaperNames String,
   win32PrinterPortName String,
   win32PrinterPrintJobDataType String,
   win32PrinterSeparatorFile String,
   win32PrinterServerName String,
   win32PrinterShareName String,
   win32PrinterStartTime Datetime,
   win32PrinterUntilTime Datetime,
   win32PrinterDefaultPriority Uint32,
   win32PrinterAveragePagesPerMinute Uint32,
   win32PrinterPrintProcessor String,
   win32PrinterStatus String
}

win32PrinterKeyIndex OBJECT-TYPE
   SYNTAX         String
   ACCESS         read-write
   STATUS         mandatory
   DESCRIPTION    ""
   REFERENCE      "Win32_Printer.KeyIndex"
::= { win32PrinterEntry 1 }

win32PrinterAttributes OBJECT-TYPE
   SYNTAX         Uint32
   ACCESS         read-write
   STATUS         mandatory
   DESCRIPTION    "The Attributes property indicates the attributes of the Win32 printing device.<P>Example: 64"
   REFERENCE      "Win32_Printer.Attributes"
::= { win32PrinterEntry 2 }

win32PrinterDriverName OBJECT-TYPE
   SYNTAX         String
   ACCESS         read-write
   STATUS         mandatory
   DESCRIPTION    "The DriverName property indicates the driver name of the Win32 printing device.<P>Example: Windows NT Fax Driver"
   REFERENCE      "Win32_Printer.DriverName"
::= { win32PrinterEntry 3 }

win32PrinterLocation OBJECT-TYPE
   SYNTAX         String
   ACCESS         read-write
   STATUS         mandatory
   DESCRIPTION    "The Location property indicates the location of the Win32 printing device."
   REFERENCE      "Win32_Printer.Location"
::= { win32PrinterEntry 4 }

win32PrinterPrinterPaperNames OBJECT-TYPE
   SYNTAX         String
   ACCESS         read-write
   STATUS         mandatory
   DESCRIPTION    "The PrinterPaperNames property indicates the list of paper sizes supported by the printer using the printer specified names for the paper sizes.<P>Example: B5 (JIS)"
   REFERENCE      "Win32_Printer.PrinterPaperNames"
::= { win32PrinterEntry 5 }

win32PrinterPortName OBJECT-TYPE
   SYNTAX         String
   ACCESS         read-write
   STATUS         mandatory
   DESCRIPTION    "The PortName property indicates the port name of the Win32 printing device.<P>Example: Sportster 56000 Fax Internal"
   REFERENCE      "Win32_Printer.PortName"
::= { win32PrinterEntry 6 }

win32PrinterPrintJobDataType OBJECT-TYPE
   SYNTAX         String
   ACCESS         read-write
   STATUS         mandatory
   DESCRIPTION    "The PrintJobDataType property indicates the data type of the print job pending on the Win32 printing device."
   REFERENCE      "Win32_Printer.PrintJobDataType"
::= { win32PrinterEntry 7 }

win32PrinterSeparatorFile OBJECT-TYPE
   SYNTAX         String
   ACCESS         read-write
   STATUS         mandatory
   DESCRIPTION    "The SeparatorFile property indicates the file printed between print jobs."
   REFERENCE      "Win32_Printer.SeparatorFile"
::= { win32PrinterEntry 8 }

win32PrinterServerName OBJECT-TYPE
   SYNTAX         String
   ACCESS         read-write
   STATUS         mandatory
   DESCRIPTION    "The ServerName property indicates the name of the server hosting the Win32 printing device."
   REFERENCE      "Win32_Printer.ServerName"
::= { win32PrinterEntry 9 }

win32PrinterShareName OBJECT-TYPE
   SYNTAX         String
   ACCESS         read-write
   STATUS         mandatory
   DESCRIPTION    "The ShareName property indicates the share name of the Win32 printing device.<P>Example: \\\\PRINTSERVER1\\PRINTER2"
   REFERENCE      "Win32_Printer.ShareName"
::= { win32PrinterEntry 10 }

win32PrinterStartTime OBJECT-TYPE
   SYNTAX         Datetime
   ACCESS         read-write
   STATUS         mandatory
   DESCRIPTION    "The StartTime property specifies the earliest time at which the printer will print a job if the printer has been limited to print only at certain times."
   REFERENCE      "Win32_Printer.StartTime"
::= { win32PrinterEntry 11 }

win32PrinterUntilTime OBJECT-TYPE
   SYNTAX         Datetime
   ACCESS         read-write
   STATUS         mandatory
   DESCRIPTION    "The UntilTime property specifies the latest time at which the printer will print a job if the printer has been limited to print only at certain times."
   REFERENCE      "Win32_Printer.UntilTime"
::= { win32PrinterEntry 12 }

win32PrinterDefaultPriority OBJECT-TYPE
   SYNTAX         Uint32
   ACCESS         read-write
   STATUS         mandatory
   DESCRIPTION    "The DefaultPriority property specifies the default priority value assigned to each print job."
   REFERENCE      "Win32_Printer.DefaultPriority"
::= { win32PrinterEntry 13 }

win32PrinterAveragePagesPerMinute OBJECT-TYPE
   SYNTAX         Uint32
   ACCESS         read-write
   STATUS         mandatory
   DESCRIPTION    "The AveragePagesPerMinute property specifies the average number of pages per minute that have been printed on the printer."
   REFERENCE      "Win32_Printer.AveragePagesPerMinute"
::= { win32PrinterEntry 14 }

win32PrinterPrintProcessor OBJECT-TYPE
   SYNTAX         String
   ACCESS         read-write
   STATUS         mandatory
   DESCRIPTION    "The PrintProcessor property specifies the name of the print processor used by the printer."
   REFERENCE      "Win32_Printer.PrintProcessor"
::= { win32PrinterEntry 15 }

win32PrinterStatus OBJECT-TYPE
   SYNTAX         String
   ACCESS         read-write
   STATUS         mandatory
   DESCRIPTION    "The Status property is a string indicating the current status of the object. Various operational and non-operational statuses can be defined. Operational statuses are OK, Degraded and Pred Fail. Pred Fail indicates that an element may be functioning properly but predicting a failure in the near future. An example is a SMART-enabled hard drive. Non-operational statuses can also be specified. These are Error, Starting, Stopping and Service. The latter, Service, could apply during mirror-resilvering of a disk, reload of a user permissions list, or other administrative work. Not all such work is on-line, yet the managed element is neither OK nor in one of the other states."
   REFERENCE      "Win32_Printer.Status"
::= { win32PrinterEntry 16 }

win32UninterruptiblePowerSupplyTable OBJECT-TYPE
   SYNTAX         SEQUENCE OF Win32UninterruptiblePowerSupplyEntry
   ACCESS         not-accessible
   STATUS         mandatory
   DESCRIPTION    "The Win32_UninterruptiblePowerSupply class represents a device that supplies electrical current to other parts of the system."
   REFERENCE      "Win32_UninterruptiblePowerSupply"
::= { win32WMI 130 }

win32UninterruptiblePowerSupplyEntry OBJECT-TYPE
   SYNTAX         Win32UninterruptiblePowerSupplyEntry
   ACCESS         not-accessible
   STATUS         mandatory
   DESCRIPTION    ""
   INDEX          { win32UninterruptiblePowerSupplyKeyIndex }
::= { win32UninterruptiblePowerSupplyTable 1 }

Win32UninterruptiblePowerSupplyEntry ::= SEQUENCE
{
   win32UninterruptiblePowerSupplyKeyIndex String,
   win32UninterruptiblePowerSupplyBatteryInstalled Boolean,
   win32UninterruptiblePowerSupplyCanTurnOffRemotely Boolean,
   win32UninterruptiblePowerSupplyCommandFile String,
   win32UninterruptiblePowerSupplyFirstMessageDelay Uint32,
   win32UninterruptiblePowerSupplyLowBatterySignal Boolean,
   win32UninterruptiblePowerSupplyMessageInterval Uint32,
   win32UninterruptiblePowerSupplyPowerFailSignal Boolean,
   win32UninterruptiblePowerSupplyUPSPort String,
   win32UninterruptiblePowerSupplyStatus String
}

win32UninterruptiblePowerSupplyKeyIndex OBJECT-TYPE
   SYNTAX         String
   ACCESS         read-write
   STATUS         mandatory
   DESCRIPTION    ""
   REFERENCE      "Win32_UninterruptiblePowerSupply.KeyIndex"
::= { win32UninterruptiblePowerSupplyEntry 1 }

win32UninterruptiblePowerSupplyBatteryInstalled OBJECT-TYPE
   SYNTAX         Boolean
   ACCESS         read-write
   STATUS         mandatory
   DESCRIPTION    "The BatteryInstalled property determines whether there is a battery installed on the device.<P>Values: TRUE or FALSE. If TRUE, a battery is installed."
   REFERENCE      "Win32_UninterruptiblePowerSupply.BatteryInstalled"
::= { win32UninterruptiblePowerSupplyEntry 2 }

win32UninterruptiblePowerSupplyCanTurnOffRemotely OBJECT-TYPE
   SYNTAX         Boolean
   ACCESS         read-write
   STATUS         mandatory
   DESCRIPTION    "The CanTurnOffRemotely property determines whether the power supply can be turned off remotely.<P>Values: TRUE or FALSE. If TRUE, the power supply can be turned off remotely."
   REFERENCE      "Win32_UninterruptiblePowerSupply.CanTurnOffRemotely"
::= { win32UninterruptiblePowerSupplyEntry 3 }

win32UninterruptiblePowerSupplyCommandFile OBJECT-TYPE
   SYNTAX         String
   ACCESS         read-write
   STATUS         mandatory
   DESCRIPTION    "The CommandFile property indicates the command file of the power supply."
   REFERENCE      "Win32_UninterruptiblePowerSupply.CommandFile"
::= { win32UninterruptiblePowerSupplyEntry 4 }

win32UninterruptiblePowerSupplyFirstMessageDelay OBJECT-TYPE
   SYNTAX         Uint32
   ACCESS         read-write
   STATUS         mandatory
   DESCRIPTION    ""
   REFERENCE      "Win32_UninterruptiblePowerSupply.FirstMessageDelay"
::= { win32UninterruptiblePowerSupplyEntry 5 }

win32UninterruptiblePowerSupplyLowBatterySignal OBJECT-TYPE
   SYNTAX         Boolean
   ACCESS         read-write
   STATUS         mandatory
   DESCRIPTION    "The LowBatterySignal property determines whether the power supply has a low battery signal.<P>Values: TRUE or FALSE. If TRUE, the power supply has a low battery signal."
   REFERENCE      "Win32_UninterruptiblePowerSupply.LowBatterySignal"
::= { win32UninterruptiblePowerSupplyEntry 6 }

win32UninterruptiblePowerSupplyMessageInterval OBJECT-TYPE
   SYNTAX         Uint32
   ACCESS         read-write
   STATUS         mandatory
   DESCRIPTION    "The MessageInterval property indicates the interval between error messages generated by this device."
   REFERENCE      "Win32_UninterruptiblePowerSupply.MessageInterval"
::= { win32UninterruptiblePowerSupplyEntry 7 }

win32UninterruptiblePowerSupplyPowerFailSignal OBJECT-TYPE
   SYNTAX         Boolean
   ACCESS         read-write
   STATUS         mandatory
   DESCRIPTION    "The PowerFailSignal property determines whether the power supply  has a power failure signal.<P>Values: TRUE or FALSE. If TRUE, the power supply has a power failure signal."
   REFERENCE      "Win32_UninterruptiblePowerSupply.PowerFailSignal"
::= { win32UninterruptiblePowerSupplyEntry 8 }

win32UninterruptiblePowerSupplyUPSPort OBJECT-TYPE
   SYNTAX         String
   ACCESS         read-write
   STATUS         mandatory
   DESCRIPTION    "The UPSPort property indicates the UPS port for the power supply."
   REFERENCE      "Win32_UninterruptiblePowerSupply.UPSPort"
::= { win32UninterruptiblePowerSupplyEntry 9 }

win32UninterruptiblePowerSupplyStatus OBJECT-TYPE
   SYNTAX         String
   ACCESS         read-write
   STATUS         mandatory
   DESCRIPTION    "The Status property is a string indicating the current status of the object. Various operational and non-operational statuses can be defined. Operational statuses are OK, Degraded and Pred Fail. Pred Fail indicates that an element may be functioning properly but predicting a failure in the near future. An example is a SMART-enabled hard drive. Non-operational statuses can also be specified. These are Error, Starting, Stopping and Service. The latter, Service, could apply during mirror-resilvering of a disk, reload of a user permissions list, or other administrative work. Not all such work is on-line, yet the managed element is neither OK nor in one of the other states."
   REFERENCE      "Win32_UninterruptiblePowerSupply.Status"
::= { win32UninterruptiblePowerSupplyEntry 10 }

win32POTSModemTable OBJECT-TYPE
   SYNTAX         SEQUENCE OF Win32POTSModemEntry
   ACCESS         not-accessible
   STATUS         mandatory
   DESCRIPTION    "The Win32_POTSModem class represents a Plain Old Telephone Service (POTS) modem on a Win32 system."
   REFERENCE      "Win32_POTSModem"
::= { win32WMI 140 }

win32POTSModemEntry OBJECT-TYPE
   SYNTAX         Win32POTSModemEntry
   ACCESS         not-accessible
   STATUS         mandatory
   DESCRIPTION    ""
   INDEX          { win32POTSModemKeyIndex }
::= { win32POTSModemTable 1 }

Win32POTSModemEntry ::= SEQUENCE
{
   win32POTSModemKeyIndex String,
   win32POTSModemAttachedTo String,
   win32POTSModemBlindOff String,
   win32POTSModemBlindOn String,
   win32POTSModemCompatibilityFlags String,
   win32POTSModemCompressionOff String,
   win32POTSModemCompressionOn String,
   win32POTSModemConfigurationDialog String,
   win32POTSModemDCB Uint8,
   win32POTSModemDefault Uint8,
   win32POTSModemDeviceLoader String,
   win32POTSModemDeviceType String,
   win32POTSModemDriverDate Datetime,
   win32POTSModemErrorControlForced String,
   win32POTSModemErrorControlOff String,
   win32POTSModemErrorControlOn String,
   win32POTSModemFlowControlHard String,
   win32POTSModemFlowControlSoft String,
   win32POTSModemFlowControlOff String,
   win32POTSModemInactivityScale String,
   win32POTSModemIndex Uint32,
   win32POTSModemModel String,
   win32POTSModemModemInfPath String,
   win32POTSModemModemInfSection String,
   win32POTSModemModulationBell String,
   win32POTSModemModulationCCITT String,
   win32POTSModemPortSubClass String,
   win32POTSModemPrefix String,
   win32POTSModemProperties Uint8,
   win32POTSModemProviderName String,
   win32POTSModemPulse String,
   win32POTSModemReset String,
   win32POTSModemResponsesKeyName String,
   win32POTSModemSpeakerModeDial String,
   win32POTSModemSpeakerModeOff String,
   win32POTSModemSpeakerModeOn String,
   win32POTSModemSpeakerModeSetup String,
   win32POTSModemSpeakerVolumeHigh String,
   win32POTSModemSpeakerVolumeLow String,
   win32POTSModemSpeakerVolumeMed String,
   win32POTSModemStringFormat String,
   win32POTSModemTerminator String,
   win32POTSModemTone String,
   win32POTSModemVoiceSwitchFeature String,
   win32POTSModemStatus String
}

win32POTSModemKeyIndex OBJECT-TYPE
   SYNTAX         String
   ACCESS         read-write
   STATUS         mandatory
   DESCRIPTION    ""
   REFERENCE      "Win32_POTSModem.KeyIndex"
::= { win32POTSModemEntry 1 }

win32POTSModemAttachedTo OBJECT-TYPE
   SYNTAX         String
   ACCESS         read-write
   STATUS         mandatory
   DESCRIPTION    "The Attached property indicates the port to which the POTS modem is attached.<P>Example: COM1"
   REFERENCE      "Win32_POTSModem.AttachedTo"
::= { win32POTSModemEntry 2 }

win32POTSModemBlindOff OBJECT-TYPE
   SYNTAX         String
   ACCESS         read-write
   STATUS         mandatory
   DESCRIPTION    ""
   REFERENCE      "Win32_POTSModem.BlindOff"
::= { win32POTSModemEntry 3 }

win32POTSModemBlindOn OBJECT-TYPE
   SYNTAX         String
   ACCESS         read-write
   STATUS         mandatory
   DESCRIPTION    ""
   REFERENCE      "Win32_POTSModem.BlindOn"
::= { win32POTSModemEntry 4 }

win32POTSModemCompatibilityFlags OBJECT-TYPE
   SYNTAX         String
   ACCESS         read-write
   STATUS         mandatory
   DESCRIPTION    ""
   REFERENCE      "Win32_POTSModem.CompatibilityFlags"
::= { win32POTSModemEntry 5 }

win32POTSModemCompressionOff OBJECT-TYPE
   SYNTAX         String
   ACCESS         read-write
   STATUS         mandatory
   DESCRIPTION    "The CompressionOff property indicates that data compression is off."
   REFERENCE      "Win32_POTSModem.CompressionOff"
::= { win32POTSModemEntry 6 }

win32POTSModemCompressionOn OBJECT-TYPE
   SYNTAX         String
   ACCESS         read-write
   STATUS         mandatory
   DESCRIPTION    "The ComprerssionOn property indicates that data compression is on."
   REFERENCE      "Win32_POTSModem.CompressionOn"
::= { win32POTSModemEntry 7 }

win32POTSModemConfigurationDialog OBJECT-TYPE
   SYNTAX         String
   ACCESS         read-write
   STATUS         mandatory
   DESCRIPTION    ""
   REFERENCE      "Win32_POTSModem.ConfigurationDialog"
::= { win32POTSModemEntry 8 }

win32POTSModemDCB OBJECT-TYPE
   SYNTAX         Uint8
   ACCESS         read-write
   STATUS         mandatory
   DESCRIPTION    ""
   REFERENCE      "Win32_POTSModem.DCB"
::= { win32POTSModemEntry 9 }

win32POTSModemDefault OBJECT-TYPE
   SYNTAX         Uint8
   ACCESS         read-write
   STATUS         mandatory
   DESCRIPTION    "The Default property indicates that this POTS modem is the default modem on the Win32 system."
   REFERENCE      "Win32_POTSModem.Default"
::= { win32POTSModemEntry 10 }

win32POTSModemDeviceLoader OBJECT-TYPE
   SYNTAX         String
   ACCESS         read-write
   STATUS         mandatory
   DESCRIPTION    "The DeviceLoader property indicates the name of the device loader for the modem."
   REFERENCE      "Win32_POTSModem.DeviceLoader"
::= { win32POTSModemEntry 11 }

win32POTSModemDeviceType OBJECT-TYPE
   SYNTAX         String
   ACCESS         read-write
   STATUS         mandatory
   DESCRIPTION    "The DeviceType property indicates the type of device."
   REFERENCE      "Win32_POTSModem.DeviceType"
::= { win32POTSModemEntry 12 }

win32POTSModemDriverDate OBJECT-TYPE
   SYNTAX         Datetime
   ACCESS         read-write
   STATUS         mandatory
   DESCRIPTION    "The DriverDate propety indicates the date of the modem driver."
   REFERENCE      "Win32_POTSModem.DriverDate"
::= { win32POTSModemEntry 13 }

win32POTSModemErrorControlForced OBJECT-TYPE
   SYNTAX         String
   ACCESS         read-write
   STATUS         mandatory
   DESCRIPTION    "The ErrorControlForced property indicates that error control is forced."
   REFERENCE      "Win32_POTSModem.ErrorControlForced"
::= { win32POTSModemEntry 14 }

win32POTSModemErrorControlOff OBJECT-TYPE
   SYNTAX         String
   ACCESS         read-write
   STATUS         mandatory
   DESCRIPTION    "The ErrorControlOff property indicates that the error control is off."
   REFERENCE      "Win32_POTSModem.ErrorControlOff"
::= { win32POTSModemEntry 15 }

win32POTSModemErrorControlOn OBJECT-TYPE
   SYNTAX         String
   ACCESS         read-write
   STATUS         mandatory
   DESCRIPTION    "The ErrorControlOn property indicates that the error control is on."
   REFERENCE      "Win32_POTSModem.ErrorControlOn"
::= { win32POTSModemEntry 16 }

win32POTSModemFlowControlHard OBJECT-TYPE
   SYNTAX         String
   ACCESS         read-write
   STATUS         mandatory
   DESCRIPTION    "The FlowControlHard property indicates that hardware flow control is being used."
   REFERENCE      "Win32_POTSModem.FlowControlHard"
::= { win32POTSModemEntry 17 }

win32POTSModemFlowControlSoft OBJECT-TYPE
   SYNTAX         String
   ACCESS         read-write
   STATUS         mandatory
   DESCRIPTION    "The FlowControlSoft property indicates that software flow control is being used."
   REFERENCE      "Win32_POTSModem.FlowControlSoft"
::= { win32POTSModemEntry 18 }

win32POTSModemFlowControlOff OBJECT-TYPE
   SYNTAX         String
   ACCESS         read-write
   STATUS         mandatory
   DESCRIPTION    "The FlowControlOff property indicates that flow control is off."
   REFERENCE      "Win32_POTSModem.FlowControlOff"
::= { win32POTSModemEntry 19 }

win32POTSModemInactivityScale OBJECT-TYPE
   SYNTAX         String
   ACCESS         read-write
   STATUS         mandatory
   DESCRIPTION    ""
   REFERENCE      "Win32_POTSModem.InactivityScale"
::= { win32POTSModemEntry 20 }

win32POTSModemIndex OBJECT-TYPE
   SYNTAX         Uint32
   ACCESS         read-write
   STATUS         mandatory
   DESCRIPTION    "The Index property indicates the index number for this POTS modem.<P>Example: 0"
   REFERENCE      "Win32_POTSModem.Index"
::= { win32POTSModemEntry 21 }

win32POTSModemModel OBJECT-TYPE
   SYNTAX         String
   ACCESS         read-write
   STATUS         mandatory
   DESCRIPTION    "The Model property indicates the model of the POTS modem.<P>Example: Sportster 56K External"
   REFERENCE      "Win32_POTSModem.Model"
::= { win32POTSModemEntry 22 }

win32POTSModemModemInfPath OBJECT-TYPE
   SYNTAX         String
   ACCESS         read-write
   STATUS         mandatory
   DESCRIPTION    "The ModemInfPath property indicates the path to the modem INF file.<P>Example: C:\\WINNT\\INF"
   REFERENCE      "Win32_POTSModem.ModemInfPath"
::= { win32POTSModemEntry 23 }

win32POTSModemModemInfSection OBJECT-TYPE
   SYNTAX         String
   ACCESS         read-write
   STATUS         mandatory
   DESCRIPTION    "The ModemInfSection property indicates the name of the section in the modem INF file that contains information about the modem."
   REFERENCE      "Win32_POTSModem.ModemInfSection"
::= { win32POTSModemEntry 24 }

win32POTSModemModulationBell OBJECT-TYPE
   SYNTAX         String
   ACCESS         read-write
   STATUS         mandatory
   DESCRIPTION    ""
   REFERENCE      "Win32_POTSModem.ModulationBell"
::= { win32POTSModemEntry 25 }

win32POTSModemModulationCCITT OBJECT-TYPE
   SYNTAX         String
   ACCESS         read-write
   STATUS         mandatory
   DESCRIPTION    ""
   REFERENCE      "Win32_POTSModem.ModulationCCITT"
::= { win32POTSModemEntry 26 }

win32POTSModemPortSubClass OBJECT-TYPE
   SYNTAX         String
   ACCESS         read-write
   STATUS         mandatory
   DESCRIPTION    ""
   REFERENCE      "Win32_POTSModem.PortSubClass"
::= { win32POTSModemEntry 27 }

win32POTSModemPrefix OBJECT-TYPE
   SYNTAX         String
   ACCESS         read-write
   STATUS         mandatory
   DESCRIPTION    "The Prefix property indicates the dialing prefix for outside line access."
   REFERENCE      "Win32_POTSModem.Prefix"
::= { win32POTSModemEntry 28 }

win32POTSModemProperties OBJECT-TYPE
   SYNTAX         Uint8
   ACCESS         read-write
   STATUS         mandatory
   DESCRIPTION    "The Properties property is a string array that list all the properties (and their values) for the POTS Modem."
   REFERENCE      "Win32_POTSModem.Properties"
::= { win32POTSModemEntry 29 }

win32POTSModemProviderName OBJECT-TYPE
   SYNTAX         String
   ACCESS         read-write
   STATUS         mandatory
   DESCRIPTION    "The ProviderName property indicates the name of the provider for this POTS modem."
   REFERENCE      "Win32_POTSModem.ProviderName"
::= { win32POTSModemEntry 30 }

win32POTSModemPulse OBJECT-TYPE
   SYNTAX         String
   ACCESS         read-write
   STATUS         mandatory
   DESCRIPTION    "The Pulse property indicates that pulse mode is used for dialing."
   REFERENCE      "Win32_POTSModem.Pulse"
::= { win32POTSModemEntry 31 }

win32POTSModemReset OBJECT-TYPE
   SYNTAX         String
   ACCESS         read-write
   STATUS         mandatory
   DESCRIPTION    "The Reset property indicates that the modem has been reset for the next call."
   REFERENCE      "Win32_POTSModem.Reset"
::= { win32POTSModemEntry 32 }

win32POTSModemResponsesKeyName OBJECT-TYPE
   SYNTAX         String
   ACCESS         read-write
   STATUS         mandatory
   DESCRIPTION    ""
   REFERENCE      "Win32_POTSModem.ResponsesKeyName"
::= { win32POTSModemEntry 33 }

win32POTSModemSpeakerModeDial OBJECT-TYPE
   SYNTAX         String
   ACCESS         read-write
   STATUS         mandatory
   DESCRIPTION    "The SpeakerModeDial property indicates that the speaker is on only during the dial-up sequence."
   REFERENCE      "Win32_POTSModem.SpeakerModeDial"
::= { win32POTSModemEntry 34 }

win32POTSModemSpeakerModeOff OBJECT-TYPE
   SYNTAX         String
   ACCESS         read-write
   STATUS         mandatory
   DESCRIPTION    "The SpeakerModeOff property indicates that the speaker mode is off."
   REFERENCE      "Win32_POTSModem.SpeakerModeOff"
::= { win32POTSModemEntry 35 }

win32POTSModemSpeakerModeOn OBJECT-TYPE
   SYNTAX         String
   ACCESS         read-write
   STATUS         mandatory
   DESCRIPTION    "The SpeakerModeOn property indicates that the speaker mode is on."
   REFERENCE      "Win32_POTSModem.SpeakerModeOn"
::= { win32POTSModemEntry 36 }

win32POTSModemSpeakerModeSetup OBJECT-TYPE
   SYNTAX         String
   ACCESS         read-write
   STATUS         mandatory
   DESCRIPTION    "The SpeakerModeSetup indicates settings for the speaker mode."
   REFERENCE      "Win32_POTSModem.SpeakerModeSetup"
::= { win32POTSModemEntry 37 }

win32POTSModemSpeakerVolumeHigh OBJECT-TYPE
   SYNTAX         String
   ACCESS         read-write
   STATUS         mandatory
   DESCRIPTION    "The SpeakerVolumeHigh property indicates that the speaker volume is set at high volume."
   REFERENCE      "Win32_POTSModem.SpeakerVolumeHigh"
::= { win32POTSModemEntry 38 }

win32POTSModemSpeakerVolumeLow OBJECT-TYPE
   SYNTAX         String
   ACCESS         read-write
   STATUS         mandatory
   DESCRIPTION    "The SpeakerVolumeLow property indicates that the speaker volume is set at low volume."
   REFERENCE      "Win32_POTSModem.SpeakerVolumeLow"
::= { win32POTSModemEntry 39 }

win32POTSModemSpeakerVolumeMed OBJECT-TYPE
   SYNTAX         String
   ACCESS         read-write
   STATUS         mandatory
   DESCRIPTION    "The SpeakerVolumeMed property indicates that the speaker volume is set at medium volume."
   REFERENCE      "Win32_POTSModem.SpeakerVolumeMed"
::= { win32POTSModemEntry 40 }

win32POTSModemStringFormat OBJECT-TYPE
   SYNTAX         String
   ACCESS         read-write
   STATUS         mandatory
   DESCRIPTION    "The StringFormat property indicates the AT initialization string to be used when dialing a number."
   REFERENCE      "Win32_POTSModem.StringFormat"
::= { win32POTSModemEntry 41 }

win32POTSModemTerminator OBJECT-TYPE
   SYNTAX         String
   ACCESS         read-write
   STATUS         mandatory
   DESCRIPTION    ""
   REFERENCE      "Win32_POTSModem.Terminator"
::= { win32POTSModemEntry 42 }

win32POTSModemTone OBJECT-TYPE
   SYNTAX         String
   ACCESS         read-write
   STATUS         mandatory
   DESCRIPTION    "The Tone property indicates that tone mode is used for dialing."
   REFERENCE      "Win32_POTSModem.Tone"
::= { win32POTSModemEntry 43 }

win32POTSModemVoiceSwitchFeature OBJECT-TYPE
   SYNTAX         String
   ACCESS         read-write
   STATUS         mandatory
   DESCRIPTION    ""
   REFERENCE      "Win32_POTSModem.VoiceSwitchFeature"
::= { win32POTSModemEntry 44 }

win32POTSModemStatus OBJECT-TYPE
   SYNTAX         String
   ACCESS         read-write
   STATUS         mandatory
   DESCRIPTION    "The Status property is a string indicating the current status of the object. Various operational and non-operational statuses can be defined. Operational statuses are OK, Degraded and Pred Fail. Pred Fail indicates that an element may be functioning properly but predicting a failure in the near future. An example is a SMART-enabled hard drive. Non-operational statuses can also be specified. These are Error, Starting, Stopping and Service. The latter, Service, could apply during mirror-resilvering of a disk, reload of a user permissions list, or other administrative work. Not all such work is on-line, yet the managed element is neither OK nor in one of the other states."
   REFERENCE      "Win32_POTSModem.Status"
::= { win32POTSModemEntry 45 }

win32SerialPortTable OBJECT-TYPE
   SYNTAX         SEQUENCE OF Win32SerialPortEntry
   ACCESS         not-accessible
   STATUS         mandatory
   DESCRIPTION    "The Win32_SerialPort class represents a serial port on a Win32 system."
   REFERENCE      "Win32_SerialPort"
::= { win32WMI 150 }

win32SerialPortEntry OBJECT-TYPE
   SYNTAX         Win32SerialPortEntry
   ACCESS         not-accessible
   STATUS         mandatory
   DESCRIPTION    ""
   INDEX          { win32SerialPortKeyIndex }
::= { win32SerialPortTable 1 }

Win32SerialPortEntry ::= SEQUENCE
{
   win32SerialPortKeyIndex String,
   win32SerialPortBinary Boolean,
   win32SerialPortMaximumInputBufferSize Uint32,
   win32SerialPortMaximumOutputBufferSize Uint32,
   win32SerialPortProviderType String,
   win32SerialPortSettableBaudRate Boolean,
   win32SerialPortSettableDataBits Boolean,
   win32SerialPortSettableFlowControl Boolean,
   win32SerialPortSettableParity Boolean,
   win32SerialPortSettableParityCheck Boolean,
   win32SerialPortSettableRLSD Boolean,
   win32SerialPortSettableStopBits Boolean,
   win32SerialPortSupports16BitMode Boolean,
   win32SerialPortSupportsDTRDSR Boolean,
   win32SerialPortSupportsElapsedTimeouts Boolean,
   win32SerialPortSupportsIntTimeouts Boolean,
   win32SerialPortSupportsParityCheck Boolean,
   win32SerialPortSupportsRLSD Boolean,
   win32SerialPortSupportsRTSCTS Boolean,
   win32SerialPortSupportsSpecialCharacters Boolean,
   win32SerialPortSupportsXOnXOff Boolean,
   win32SerialPortSupportsXOnXOffSet Boolean,
   win32SerialPortStatus String
}

win32SerialPortKeyIndex OBJECT-TYPE
   SYNTAX         String
   ACCESS         read-write
   STATUS         mandatory
   DESCRIPTION    ""
   REFERENCE      "Win32_SerialPort.KeyIndex"
::= { win32SerialPortEntry 1 }

win32SerialPortBinary OBJECT-TYPE
   SYNTAX         Boolean
   ACCESS         read-write
   STATUS         mandatory
   DESCRIPTION    "The Binary property determines whether the serial port is configured for binary data transfer. Values: TRUE or FALSE. If TRUE, the serial port is configured for binary data transfer."
   REFERENCE      "Win32_SerialPort.Binary"
::= { win32SerialPortEntry 2 }

win32SerialPortMaximumInputBufferSize OBJECT-TYPE
   SYNTAX         Uint32
   ACCESS         read-write
   STATUS         mandatory
   DESCRIPTION    "The MaximumInputBufferSize property indicates the maximum input buffer size for this serial port."
   REFERENCE      "Win32_SerialPort.MaximumInputBufferSize"
::= { win32SerialPortEntry 3 }

win32SerialPortMaximumOutputBufferSize OBJECT-TYPE
   SYNTAX         Uint32
   ACCESS         read-write
   STATUS         mandatory
   DESCRIPTION    "The MaximumOutputBufferSize property indicates the maximum output buffer size for this serial port."
   REFERENCE      "Win32_SerialPort.MaximumOutputBufferSize"
::= { win32SerialPortEntry 4 }

win32SerialPortProviderType OBJECT-TYPE
   SYNTAX         String
   ACCESS         read-write
   STATUS         mandatory
   DESCRIPTION    "The ProviderType property indicates the provider type for this serial port."
   REFERENCE      "Win32_SerialPort.ProviderType"
::= { win32SerialPortEntry 5 }

win32SerialPortSettableBaudRate OBJECT-TYPE
   SYNTAX         Boolean
   ACCESS         read-write
   STATUS         mandatory
   DESCRIPTION    "The SettableBaudRate property determines whether the baud rate is settable for this serial port.<P>Values: TRUE or FALSE. If TRUE, the baud rate is settable."
   REFERENCE      "Win32_SerialPort.SettableBaudRate"
::= { win32SerialPortEntry 6 }

win32SerialPortSettableDataBits OBJECT-TYPE
   SYNTAX         Boolean
   ACCESS         read-write
   STATUS         mandatory
   DESCRIPTION    "The SettableDataBits property determines whether data bits are settable for this serial port.<P>Values: TRUE or FALSE. If TRUE, data bits are settable."
   REFERENCE      "Win32_SerialPort.SettableDataBits"
::= { win32SerialPortEntry 7 }

win32SerialPortSettableFlowControl OBJECT-TYPE
   SYNTAX         Boolean
   ACCESS         read-write
   STATUS         mandatory
   DESCRIPTION    "The SettableFlowControl property determines whether flow control is settable for this serial port.<P>Values: TRUE or FALSE. If TRUE, flow control is settable."
   REFERENCE      "Win32_SerialPort.SettableFlowControl"
::= { win32SerialPortEntry 8 }

win32SerialPortSettableParity OBJECT-TYPE
   SYNTAX         Boolean
   ACCESS         read-write
   STATUS         mandatory
   DESCRIPTION    "The SettableParity property determines whether parity is settable for this serial port.<P>Values: TRUE or FALSE. If TRUE, parity is settable."
   REFERENCE      "Win32_SerialPort.SettableParity"
::= { win32SerialPortEntry 9 }

win32SerialPortSettableParityCheck OBJECT-TYPE
   SYNTAX         Boolean
   ACCESS         read-write
   STATUS         mandatory
   DESCRIPTION    "The SettableParityCheck property determines whether parity check is settable for this serial port.<P>Values: TRUE or FALSE. If TRUE, parity check is settable."
   REFERENCE      "Win32_SerialPort.SettableParityCheck"
::= { win32SerialPortEntry 10 }

win32SerialPortSettableRLSD OBJECT-TYPE
   SYNTAX         Boolean
   ACCESS         read-write
   STATUS         mandatory
   DESCRIPTION    "The SettableRLSD property determines whether Received Line Signal Detect (RLSD) is settable for this serial port.<P>Values: TRUE or FALSE. If TRUE, RLSD is settable."
   REFERENCE      "Win32_SerialPort.SettableRLSD"
::= { win32SerialPortEntry 11 }

win32SerialPortSettableStopBits OBJECT-TYPE
   SYNTAX         Boolean
   ACCESS         read-write
   STATUS         mandatory
   DESCRIPTION    "The SettableStopBits property determines whether stop bits are settable for this serial port.<P>Values: TRUE or FALSE. If TRUE, stop bits are settable."
   REFERENCE      "Win32_SerialPort.SettableStopBits"
::= { win32SerialPortEntry 12 }

win32SerialPortSupports16BitMode OBJECT-TYPE
   SYNTAX         Boolean
   ACCESS         read-write
   STATUS         mandatory
   DESCRIPTION    "The Supports16BitMode property determines whether 16-bit mode is supported on this serial port.<P>Values: TRUE or FALSE. If TRUE, 16-bit mode is supported."
   REFERENCE      "Win32_SerialPort.Supports16BitMode"
::= { win32SerialPortEntry 13 }

win32SerialPortSupportsDTRDSR OBJECT-TYPE
   SYNTAX         Boolean
   ACCESS         read-write
   STATUS         mandatory
   DESCRIPTION    "The SupportsDTRDSR property determines whether Data Terminal Ready (DTR) and Data Set Ready (DSR) signals are supported on this serial port.<P>Values: TRUE or FALSE. If TRUE, DTR and DSR signals are supported."
   REFERENCE      "Win32_SerialPort.SupportsDTRDSR"
::= { win32SerialPortEntry 14 }

win32SerialPortSupportsElapsedTimeouts OBJECT-TYPE
   SYNTAX         Boolean
   ACCESS         read-write
   STATUS         mandatory
   DESCRIPTION    "The SettableElapsedTimeouts property determines whether elapsed timeouts are supported on this serial port.<P>Values: TRUE or FALSE. If TRUE, elapsed timeouts are supported."
   REFERENCE      "Win32_SerialPort.SupportsElapsedTimeouts"
::= { win32SerialPortEntry 15 }

win32SerialPortSupportsIntTimeouts OBJECT-TYPE
   SYNTAX         Boolean
   ACCESS         read-write
   STATUS         mandatory
   DESCRIPTION    ""
   REFERENCE      "Win32_SerialPort.SupportsIntTimeouts"
::= { win32SerialPortEntry 16 }

win32SerialPortSupportsParityCheck OBJECT-TYPE
   SYNTAX         Boolean
   ACCESS         read-write
   STATUS         mandatory
   DESCRIPTION    "The SupportsParityCheck property determines whether parity check is supported on this serial port.<P>Values: TRUE or FALSE. If TRUE, parity check is supported."
   REFERENCE      "Win32_SerialPort.SupportsParityCheck"
::= { win32SerialPortEntry 17 }

win32SerialPortSupportsRLSD OBJECT-TYPE
   SYNTAX         Boolean
   ACCESS         read-write
   STATUS         mandatory
   DESCRIPTION    "The SupportsRLSD property determines whether Received Line Signal Detect (RLSD) is supported on this serial port.<P>Values: TRUE or FALSE. If TRUE, RLSD is supported."
   REFERENCE      "Win32_SerialPort.SupportsRLSD"
::= { win32SerialPortEntry 18 }

win32SerialPortSupportsRTSCTS OBJECT-TYPE
   SYNTAX         Boolean
   ACCESS         read-write
   STATUS         mandatory
   DESCRIPTION    "The SupportsRTSCTS property determines whether Ready To Send (RTS) and Clear To Send (CTS) signals are supported on this serial port.<P>Values: TRUE or FALSE. If TRUE, RTS and CTS signals are supported."
   REFERENCE      "Win32_SerialPort.SupportsRTSCTS"
::= { win32SerialPortEntry 19 }

win32SerialPortSupportsSpecialCharacters OBJECT-TYPE
   SYNTAX         Boolean
   ACCESS         read-write
   STATUS         mandatory
   DESCRIPTION    "The SupportsSpecialCharacters property determines whether special characters are supported on this serial port.<P>Values: TRUE or FALSE. If TRUE, special characters are supported."
   REFERENCE      "Win32_SerialPort.SupportsSpecialCharacters"
::= { win32SerialPortEntry 20 }

win32SerialPortSupportsXOnXOff OBJECT-TYPE
   SYNTAX         Boolean
   ACCESS         read-write
   STATUS         mandatory
   DESCRIPTION    "The SupportsXOnXOff property determines whether XOnXOff flow control is supported on this serial port.<P>Values: TRUE or FALSE. If TRUE, XOnXOff is supported."
   REFERENCE      "Win32_SerialPort.SupportsXOnXOff"
::= { win32SerialPortEntry 21 }

win32SerialPortSupportsXOnXOffSet OBJECT-TYPE
   SYNTAX         Boolean
   ACCESS         read-write
   STATUS         mandatory
   DESCRIPTION    ""
   REFERENCE      "Win32_SerialPort.SupportsXOnXOffSet"
::= { win32SerialPortEntry 22 }

win32SerialPortStatus OBJECT-TYPE
   SYNTAX         String
   ACCESS         read-write
   STATUS         mandatory
   DESCRIPTION    "The Status property is a string indicating the current status of the object. Various operational and non-operational statuses can be defined. Operational statuses are OK, Degraded and Pred Fail. Pred Fail indicates that an element may be functioning properly but predicting a failure in the near future. An example is a SMART-enabled hard drive. Non-operational statuses can also be specified. These are Error, Starting, Stopping and Service. The latter, Service, could apply during mirror-resilvering of a disk, reload of a user permissions list, or other administrative work. Not all such work is on-line, yet the managed element is neither OK nor in one of the other states."
   REFERENCE      "Win32_SerialPort.Status"
::= { win32SerialPortEntry 23 }

win32NetworkAdapterTable OBJECT-TYPE
   SYNTAX         SEQUENCE OF Win32NetworkAdapterEntry
   ACCESS         not-accessible
   STATUS         mandatory
   DESCRIPTION    "The Win32_NetworkAdapter class represents a network adapter on a Win32 system."
   REFERENCE      "Win32_NetworkAdapter"
::= { win32WMI 160 }

win32NetworkAdapterEntry OBJECT-TYPE
   SYNTAX         Win32NetworkAdapterEntry
   ACCESS         not-accessible
   STATUS         mandatory
   DESCRIPTION    ""
   INDEX          { win32NetworkAdapterKeyIndex }
::= { win32NetworkAdapterTable 1 }

Win32NetworkAdapterEntry ::= SEQUENCE
{
   win32NetworkAdapterKeyIndex String,
   win32NetworkAdapterProductName String,
   win32NetworkAdapterAdapterType String,
   win32NetworkAdapterMACAddress String,
   win32NetworkAdapterServiceName String,
   win32NetworkAdapterManufacturer String,
   win32NetworkAdapterInstalled Boolean,
   win32NetworkAdapterIndex Uint32,
   win32NetworkAdapterMaxNumberControlled Uint32,
   win32NetworkAdapterTimeOfLastReset Datetime,
   win32NetworkAdapterStatus String
}

win32NetworkAdapterKeyIndex OBJECT-TYPE
   SYNTAX         String
   ACCESS         read-write
   STATUS         mandatory
   DESCRIPTION    ""
   REFERENCE      "Win32_NetworkAdapter.KeyIndex"
::= { win32NetworkAdapterEntry 1 }

win32NetworkAdapterProductName OBJECT-TYPE
   SYNTAX         String
   ACCESS         read-write
   STATUS         mandatory
   DESCRIPTION    "The ProductName property indicates the product name of the network adapter.<P>Example: Fast EtherLink XL"
   REFERENCE      "Win32_NetworkAdapter.ProductName"
::= { win32NetworkAdapterEntry 2 }

win32NetworkAdapterAdapterType OBJECT-TYPE
   SYNTAX         String
   ACCESS         read-write
   STATUS         mandatory
   DESCRIPTION    "The AdapterType property indicates the network adapter type."
   REFERENCE      "Win32_NetworkAdapter.AdapterType"
::= { win32NetworkAdapterEntry 3 }

win32NetworkAdapterMACAddress OBJECT-TYPE
   SYNTAX         String
   ACCESS         read-write
   STATUS         mandatory
   DESCRIPTION    "The MACAddress property indicates the media access control address for the network adapter."
   REFERENCE      "Win32_NetworkAdapter.MACAddress"
::= { win32NetworkAdapterEntry 4 }

win32NetworkAdapterServiceName OBJECT-TYPE
   SYNTAX         String
   ACCESS         read-write
   STATUS         mandatory
   DESCRIPTION    "The ServiceName property indicates the service name the network adapter."
   REFERENCE      "Win32_NetworkAdapter.ServiceName"
::= { win32NetworkAdapterEntry 5 }

win32NetworkAdapterManufacturer OBJECT-TYPE
   SYNTAX         String
   ACCESS         read-write
   STATUS         mandatory
   DESCRIPTION    "The Manufacturer property indicates the name of the network adapter manufacturer.<P>Example: 3Com"
   REFERENCE      "Win32_NetworkAdapter.Manufacturer"
::= { win32NetworkAdapterEntry 6 }

win32NetworkAdapterInstalled OBJECT-TYPE
   SYNTAX         Boolean
   ACCESS         read-write
   STATUS         mandatory
   DESCRIPTION    "The Installed property determines whether the network adapter is installed in the system.<P>Values: TRUE or FALSE. If TRUE, the network adapter is installed."
   REFERENCE      "Win32_NetworkAdapter.Installed"
::= { win32NetworkAdapterEntry 7 }

win32NetworkAdapterIndex OBJECT-TYPE
   SYNTAX         Uint32
   ACCESS         read-write
   STATUS         mandatory
   DESCRIPTION    "The Index property indicates the index number for the network adapter.<P>Example: 0"
   REFERENCE      "Win32_NetworkAdapter.Index"
::= { win32NetworkAdapterEntry 8 }

win32NetworkAdapterMaxNumberControlled OBJECT-TYPE
   SYNTAX         Uint32
   ACCESS         read-write
   STATUS         mandatory
   DESCRIPTION    "The MaxNumberControlled property indicates the maximum number of directly addressable entities supportable by this controller. A value of zero should be used if the number is unknown."
   REFERENCE      "Win32_NetworkAdapter.MaxNumberControlled"
::= { win32NetworkAdapterEntry 9 }

win32NetworkAdapterTimeOfLastReset OBJECT-TYPE
   SYNTAX         Datetime
   ACCESS         read-write
   STATUS         mandatory
   DESCRIPTION    "The TimeOfLastReset property indicates the last time the network adapter was reset."
   REFERENCE      "Win32_NetworkAdapter.TimeOfLastReset"
::= { win32NetworkAdapterEntry 10 }

win32NetworkAdapterStatus OBJECT-TYPE
   SYNTAX         String
   ACCESS         read-write
   STATUS         mandatory
   DESCRIPTION    "The Status property is a string indicating the current status of the object. Various operational and non-operational statuses can be defined. Operational statuses are OK, Degraded and Pred Fail. Pred Fail indicates that an element may be functioning properly but predicting a failure in the near future. An example is a SMART-enabled hard drive. Non-operational statuses can also be specified. These are Error, Starting, Stopping and Service. The latter, Service, could apply during mirror-resilvering of a disk, reload of a user permissions list, or other administrative work. Not all such work is on-line, yet the managed element is neither OK nor in one of the other states."
   REFERENCE      "Win32_NetworkAdapter.Status"
::= { win32NetworkAdapterEntry 11 }

win32SCSIControllerTable OBJECT-TYPE
   SYNTAX         SEQUENCE OF Win32SCSIControllerEntry
   ACCESS         not-accessible
   STATUS         mandatory
   DESCRIPTION    "The Win32_SCSIController class represents a SCSI controller on a Win32 system.<P>Example: Adaptec AHA-2940UW"
   REFERENCE      "Win32_SCSIController"
::= { win32WMI 170 }

win32SCSIControllerEntry OBJECT-TYPE
   SYNTAX         Win32SCSIControllerEntry
   ACCESS         not-accessible
   STATUS         mandatory
   DESCRIPTION    ""
   INDEX          { win32SCSIControllerKeyIndex }
::= { win32SCSIControllerTable 1 }

Win32SCSIControllerEntry ::= SEQUENCE
{
   win32SCSIControllerKeyIndex String,   
   win32SCSIControllerIndex Uint32,
   win32SCSIControllerDriverName String,
   win32SCSIControllerDeviceMap String,
   win32SCSIControllerHardwareVersion String,
   win32SCSIControllerManufacturer String,
   win32SCSIControllerStatus String
}

win32SCSIControllerKeyIndex OBJECT-TYPE
   SYNTAX         String
   ACCESS         read-write
   STATUS         mandatory
   DESCRIPTION    ""
   REFERENCE      "Win32_SCSIController.KeyIndex"
::= { win32SCSIControllerEntry 1 }

win32SCSIControllerIndex OBJECT-TYPE
   SYNTAX         Uint32
   ACCESS         read-write
   STATUS         mandatory
   DESCRIPTION    "The Index property indicates the index number of the SCSI controller.<P>Example: 0"
   REFERENCE      "Win32_SCSIController.Index"
::= { win32SCSIControllerEntry 2 }

win32SCSIControllerDriverName OBJECT-TYPE
   SYNTAX         String
   ACCESS         read-write
   STATUS         mandatory
   DESCRIPTION    "The DriverName property indicates the driver file name of the SCSI controller.<P>Example: Adaptec"
   REFERENCE      "Win32_SCSIController.DriverName"
::= { win32SCSIControllerEntry 3 }

win32SCSIControllerDeviceMap OBJECT-TYPE
   SYNTAX         String
   ACCESS         read-write
   STATUS         mandatory
   DESCRIPTION    ""
   REFERENCE      "Win32_SCSIController.DeviceMap"
::= { win32SCSIControllerEntry 4 }

win32SCSIControllerHardwareVersion OBJECT-TYPE
   SYNTAX         String
   ACCESS         read-write
   STATUS         mandatory
   DESCRIPTION    "The HardwareVersion property indicates the hardware version number of the SCSI controller.<P>Example: 1.25"
   REFERENCE      "Win32_SCSIController.HardwareVersion"
::= { win32SCSIControllerEntry 5 }

win32SCSIControllerManufacturer OBJECT-TYPE
   SYNTAX         String
   ACCESS         read-write
   STATUS         mandatory
   DESCRIPTION    "The Manufacturer property indicates the name of the SCSI controller manufacturer.<P>Example: Adaptec"
   REFERENCE      "Win32_SCSIController.Manufacturer"
::= { win32SCSIControllerEntry 6 }

win32SCSIControllerStatus OBJECT-TYPE
   SYNTAX         String
   ACCESS         read-write
   STATUS         mandatory
   DESCRIPTION    "The Status property is a string indicating the current status of the object. Various operational and non-operational statuses can be defined. Operational statuses are OK, Degraded and Pred Fail. Pred Fail indicates that an element may be functioning properly but predicting a failure in the near future. An example is a SMART-enabled hard drive. Non-operational statuses can also be specified. These are Error, Starting, Stopping and Service. The latter, Service, could apply during mirror-resilvering of a disk, reload of a user permissions list, or other administrative work. Not all such work is on-line, yet the managed element is neither OK nor in one of the other states."
   REFERENCE      "Win32_SCSIController.Status"
::= { win32SCSIControllerEntry 7 }

win32CodecFileTable OBJECT-TYPE
   SYNTAX         SEQUENCE OF Win32CodecFileEntry
   ACCESS         not-accessible
   STATUS         mandatory
   DESCRIPTION    "The Win32_CodeFile class represents the audio and visual codec installed on the system."
   REFERENCE      "Win32_CodecFile"
::= { win32WMI 190 }

win32CodecFileEntry OBJECT-TYPE
   SYNTAX         Win32CodecFileEntry
   ACCESS         not-accessible
   STATUS         mandatory
   DESCRIPTION    ""
   INDEX          { win32CodecFileKeyIndex }
::= { win32CodecFileTable 1 }

Win32CodecFileEntry ::= SEQUENCE
{
   win32CodecFileKeyIndex String,
   win32CodecFileGroup String,
   win32CodecFileDescription String,
   win32CodecFileStatus String
}

win32CodecFileKeyIndex OBJECT-TYPE
   SYNTAX         String
   ACCESS         read-write
   STATUS         mandatory
   DESCRIPTION    ""
   REFERENCE      "Win32_CodecFile.KeyIndex"
::= { win32CodecFileEntry 1 }

win32CodecFileGroup OBJECT-TYPE
   SYNTAX         String
   ACCESS         read-write
   STATUS         mandatory
   DESCRIPTION    "Codec group from registry."
   REFERENCE      "Win32_CodecFile.Group"
::= { win32CodecFileEntry 2 }

win32CodecFileDescription OBJECT-TYPE
   SYNTAX         String
   ACCESS         read-write
   STATUS         mandatory
   DESCRIPTION    "Description of Codec from registry."
   REFERENCE      "Win32_CodecFile.Description"
::= { win32CodecFileEntry 3 }

win32CodecFileStatus OBJECT-TYPE
   SYNTAX         String
   ACCESS         read-write
   STATUS         mandatory
   DESCRIPTION    "The Status property is a string indicating the current status of the object. Various operational and non-operational statuses can be defined. Operational statuses are OK, Degraded and Pred Fail. Pred Fail indicates that an element may be functioning properly but predicting a failure in the near future. An example is a SMART-enabled hard drive. Non-operational statuses can also be specified. These are Error, Starting, Stopping and Service. The latter, Service, could apply during mirror-resilvering of a disk, reload of a user permissions list, or other administrative work. Not all such work is on-line, yet the managed element is neither OK nor in one of the other states."
   REFERENCE      "Win32_CodecFile.Status"
::= { win32CodecFileEntry 4 }

win32PageFileTable OBJECT-TYPE
   SYNTAX         SEQUENCE OF Win32PageFileEntry
   ACCESS         not-accessible
   STATUS         mandatory
   DESCRIPTION    "The Win32_PageFile class represents the file used for handling virtual memory file swapping on a Win32 system.<P>Example: C:\\PAGEFILE.SYS"
   REFERENCE      "Win32_PageFile"
::= { win32WMI 210 }

win32PageFileEntry OBJECT-TYPE
   SYNTAX         Win32PageFileEntry
   ACCESS         not-accessible
   STATUS         mandatory
   DESCRIPTION    ""
   INDEX          { win32PageFileKeyIndex }
::= { win32PageFileTable 1 }

Win32PageFileEntry ::= SEQUENCE
{
   win32PageFileKeyIndex String,
   win32PageFileName String,
   win32PageFileFreeSpace Uint32,
   win32PageFileInitialSize Uint32,
   win32PageFileMaximumSize Uint32,
   win32PageFileStatus String
}

win32PageFileKeyIndex OBJECT-TYPE
   SYNTAX         String
   ACCESS         read-write
   STATUS         mandatory
   DESCRIPTION    ""
   REFERENCE      "Win32_PageFile.KeyIndex"
::= { win32PageFileEntry 1 }

win32PageFileName OBJECT-TYPE
   SYNTAX         String
   ACCESS         read-write
   STATUS         mandatory
   DESCRIPTION    "The Name property indicates the name of the page file.<P>Example: C:\\PAGEFILE.SYS"
   REFERENCE      "Win32_PageFile.Name"
::= { win32PageFileEntry 2 }

win32PageFileFreeSpace OBJECT-TYPE
   SYNTAX         Uint32
   ACCESS         read-write
   STATUS         mandatory
   DESCRIPTION    "The FreeSpace property indicates the amount of free space available in the page file."
   REFERENCE      "Win32_PageFile.FreeSpace"
::= { win32PageFileEntry 3 }

win32PageFileInitialSize OBJECT-TYPE
   SYNTAX         Uint32
   ACCESS         read-write
   STATUS         mandatory
   DESCRIPTION    "The InitialSize property indicates the initial size of the page file.<P>Example: 139MB"
   REFERENCE      "Win32_PageFile.InitialSize"
::= { win32PageFileEntry 4 }

win32PageFileMaximumSize OBJECT-TYPE
   SYNTAX         Uint32
   ACCESS         read-write
   STATUS         mandatory
   DESCRIPTION    "The MaximumSize property indicates the maximum size of the page file.<P>Example: 178MB"
   REFERENCE      "Win32_PageFile.MaximumSize"
::= { win32PageFileEntry 5 }

win32PageFileStatus OBJECT-TYPE
   SYNTAX         String
   ACCESS         read-write
   STATUS         mandatory
   DESCRIPTION    "The Status property is a string indicating the current status of the object. Various operational and non-operational statuses can be defined. Operational statuses are OK, Degraded and Pred Fail. Pred Fail indicates that an element may be functioning properly but predicting a failure in the near future. An example is a SMART-enabled hard drive. Non-operational statuses can also be specified. These are Error, Starting, Stopping and Service. The latter, Service, could apply during mirror-resilvering of a disk, reload of a user permissions list, or other administrative work. Not all such work is on-line, yet the managed element is neither OK nor in one of the other states."
   REFERENCE      "Win32_PageFile.Status"
::= { win32PageFileEntry 6 }

win32DriverVXDTable OBJECT-TYPE
   SYNTAX         SEQUENCE OF Win32DriverVXDEntry
   ACCESS         not-accessible
   STATUS         mandatory
   DESCRIPTION    "The Win32_DriverVXD class represents a virtual device driver on a Win32 system."
   REFERENCE      "Win32_DriverVXD"
::= { win32WMI 230 }

win32DriverVXDEntry OBJECT-TYPE
   SYNTAX         Win32DriverVXDEntry
   ACCESS         not-accessible
   STATUS         mandatory
   DESCRIPTION    ""
   INDEX          { win32DriverVXDKeyIndex }
::= { win32DriverVXDTable 1 }

Win32DriverVXDEntry ::= SEQUENCE
{
   win32DriverVXDKeyIndex String,
   win32DriverVXDControl String,
   win32DriverVXDDeviceDescriptorBlock String,
   win32DriverVXDPMAPI String,
   win32DriverVXDServiceTableSize Uint32,
   win32DriverVXDV86API String,
   win32DriverVXDVersion String,
   win32DriverVXDStatus String
}

win32DriverVXDKeyIndex OBJECT-TYPE
   SYNTAX         String
   ACCESS         read-write
   STATUS         mandatory
   DESCRIPTION    ""
   REFERENCE      "Win32_DriverVXD.KeyIndex"
::= { win32DriverVXDEntry 1 }

win32DriverVXDControl OBJECT-TYPE
   SYNTAX         String
   ACCESS         read-write
   STATUS         mandatory
   DESCRIPTION    ""
   REFERENCE      "Win32_DriverVXD.Control"
::= { win32DriverVXDEntry 2 }

win32DriverVXDDeviceDescriptorBlock OBJECT-TYPE
   SYNTAX         String
   ACCESS         read-write
   STATUS         mandatory
   DESCRIPTION    "The DeviceDescriptorBlock property indicates the device description block of the virtual device driver."
   REFERENCE      "Win32_DriverVXD.DeviceDescriptorBlock"
::= { win32DriverVXDEntry 3 }

win32DriverVXDPMAPI OBJECT-TYPE
   SYNTAX         String
   ACCESS         read-write
   STATUS         mandatory
   DESCRIPTION    ""
   REFERENCE      "Win32_DriverVXD.PM_API"
::= { win32DriverVXDEntry 4 }

win32DriverVXDServiceTableSize OBJECT-TYPE
   SYNTAX         Uint32
   ACCESS         read-write
   STATUS         mandatory
   DESCRIPTION    "The ServiceTableSize property indicates the service table size of the virtual device driver.<P>Example: 1024"
   REFERENCE      "Win32_DriverVXD.ServiceTableSize"
::= { win32DriverVXDEntry 5 }

win32DriverVXDV86API OBJECT-TYPE
   SYNTAX         String
   ACCESS         read-write
   STATUS         mandatory
   DESCRIPTION    ""
   REFERENCE      "Win32_DriverVXD.V86_API"
::= { win32DriverVXDEntry 6 }

win32DriverVXDVersion OBJECT-TYPE
   SYNTAX         String
   ACCESS         read-write
   STATUS         mandatory
   DESCRIPTION    "The Version property indicates the version of the VXD driver."
   REFERENCE      "Win32_DriverVXD.Version"
::= { win32DriverVXDEntry 7 }

win32DriverVXDStatus OBJECT-TYPE
   SYNTAX         String
   ACCESS         read-write
   STATUS         mandatory
   DESCRIPTION    "The Status property is a string indicating the current status of the object. Various operational and non-operational statuses can be defined. Operational statuses are OK, Degraded and Pred Fail. Pred Fail indicates that an element may be functioning properly but predicting a failure in the near future. An example is a SMART-enabled hard drive. Non-operational statuses can also be specified. These are Error, Starting, Stopping and Service. The latter, Service, could apply during mirror-resilvering of a disk, reload of a user permissions list, or other administrative work. Not all such work is on-line, yet the managed element is neither OK nor in one of the other states."
   REFERENCE      "Win32_DriverVXD.Status"
::= { win32DriverVXDEntry 8 }

win32AccountTable OBJECT-TYPE
   SYNTAX         SEQUENCE OF Win32AccountEntry
   ACCESS         not-accessible
   STATUS         mandatory
   DESCRIPTION    "The Win32_Account class represents data about a user or group that is known to the Win32 system. Any user or group data, whose name is recognized by a Windows NT domain, is a descendent (or member) of this class.<P>Example: mvotava"
   REFERENCE      "Win32_Account"
::= { win32WMI 240 }

win32AccountEntry OBJECT-TYPE
   SYNTAX         Win32AccountEntry
   ACCESS         not-accessible
   STATUS         mandatory
   DESCRIPTION    ""
   INDEX          { win32AccountKeyIndex }
::= { win32AccountTable 1 }

Win32AccountEntry ::= SEQUENCE
{
   win32AccountKeyIndex String,
   win32AccountDomain String,
   win32AccountSID String,
   win32AccountSIDType Uint8,
   win32AccountStatus String
}

win32AccountKeyIndex OBJECT-TYPE
   SYNTAX         String
   ACCESS         read-write
   STATUS         mandatory
   DESCRIPTION    ""
   REFERENCE      "Win32_Account.KeyIndex"
::= { win32AccountEntry 1 }

win32AccountDomain OBJECT-TYPE
   SYNTAX         String
   ACCESS         read-write
   STATUS         mandatory
   DESCRIPTION    "The Domain property indicates the name of the Windows NT domain to which a group or user belongs.<P>Example: NA-SALES"
   REFERENCE      "Win32_Account.Domain"
::= { win32AccountEntry 2 }

win32AccountSID OBJECT-TYPE
   SYNTAX         String
   ACCESS         read-write
   STATUS         mandatory
   DESCRIPTION    ""
   REFERENCE      "Win32_Account.SID"
::= { win32AccountEntry 3 }

win32AccountSIDType OBJECT-TYPE
   SYNTAX         Uint8
   ACCESS         read-write
   STATUS         mandatory
   DESCRIPTION    "The SIDType property indicates the SID type of the Win32 group or user."
   REFERENCE      "Win32_Account.SIDType"
::= { win32AccountEntry 4 }

win32AccountStatus OBJECT-TYPE
   SYNTAX         String
   ACCESS         read-write
   STATUS         mandatory
   DESCRIPTION    "The Status property is a string indicating the current status of the object. Various operational and non-operational statuses can be defined. Operational statuses are OK, Degraded and Pred Fail. Pred Fail indicates that an element may be functioning properly but predicting a failure in the near future. An example is a SMART-enabled hard drive. Non-operational statuses can also be specified. These are Error, Starting, Stopping and Service. The latter, Service, could apply during mirror-resilvering of a disk, reload of a user permissions list, or other administrative work. Not all such work is on-line, yet the managed element is neither OK nor in one of the other states."
   REFERENCE      "Win32_Account.Status"
::= { win32AccountEntry 5 }

win32SystemAccountTable OBJECT-TYPE
   SYNTAX         SEQUENCE OF Win32SystemAccountEntry
   ACCESS         not-accessible
   STATUS         mandatory
   DESCRIPTION    "The Win32_SystemAccount class represents data about the Win32 system."
   REFERENCE      "Win32_SystemAccount"
::= { win32WMI 250 }

win32SystemAccountEntry OBJECT-TYPE
   SYNTAX         Win32SystemAccountEntry
   ACCESS         not-accessible
   STATUS         mandatory
   DESCRIPTION    ""
   INDEX          { win32SystemAccountKeyIndex }
::= { win32SystemAccountTable 1 }

Win32SystemAccountEntry ::= SEQUENCE
{
   win32SystemAccountKeyIndex String,
   win32SystemAccountDomain String,
   win32SystemAccountName String,
   win32SystemAccountStatus String
}

win32SystemAccountKeyIndex OBJECT-TYPE
   SYNTAX         String
   ACCESS         read-write
   STATUS         mandatory
   DESCRIPTION    ""
   REFERENCE      "Win32_SystemAccount.KeyIndex"
::= { win32SystemAccountEntry 1 }

win32SystemAccountDomain OBJECT-TYPE
   SYNTAX         String
   ACCESS         read-write
   STATUS         mandatory
   DESCRIPTION    "The Domain property indicates the name of the Windows NT domain to which the system account belongs.<P>Example: NA-SALES"
   REFERENCE      "Win32_SystemAccount.Domain"
::= { win32SystemAccountEntry 2 }

win32SystemAccountName OBJECT-TYPE
   SYNTAX         String
   ACCESS         read-write
   STATUS         mandatory
   DESCRIPTION    "The Name property indicates the name of the Win32 system account."
   REFERENCE      "Win32_SystemAccount.Name"
::= { win32SystemAccountEntry 3 }

win32SystemAccountStatus OBJECT-TYPE
   SYNTAX         String
   ACCESS         read-write
   STATUS         mandatory
   DESCRIPTION    "The Status property is a string indicating the current status of the object. Various operational and non-operational statuses can be defined. Operational statuses are OK, Degraded and Pred Fail. Pred Fail indicates that an element may be functioning properly but predicting a failure in the near future. An example is a SMART-enabled hard drive. Non-operational statuses can also be specified. These are Error, Starting, Stopping and Service. The latter, Service, could apply during mirror-resilvering of a disk, reload of a user permissions list, or other administrative work. Not all such work is on-line, yet the managed element is neither OK nor in one of the other states."
   REFERENCE      "Win32_SystemAccount.Status"
::= { win32SystemAccountEntry 4 }

win32GroupTable OBJECT-TYPE
   SYNTAX         SEQUENCE OF Win32GroupEntry
   ACCESS         not-accessible
   STATUS         mandatory
   DESCRIPTION    "The Win32_Group class represents data about a group that is known to the Win32 system.<P>Example: WORKGROUP"
   REFERENCE      "Win32_Group"
::= { win32WMI 260 }

win32GroupEntry OBJECT-TYPE
   SYNTAX         Win32GroupEntry
   ACCESS         not-accessible
   STATUS         mandatory
   DESCRIPTION    ""
   INDEX          { win32GroupKeyIndex }
::= { win32GroupTable 1 }

Win32GroupEntry ::= SEQUENCE
{
   win32GroupKeyIndex String,
   win32GroupDomain String,
   win32GroupName String,
   win32GroupStatus String
}

win32GroupKeyIndex OBJECT-TYPE
   SYNTAX         String
   ACCESS         read-write
   STATUS         mandatory
   DESCRIPTION    ""
   REFERENCE      "Win32_Group.KeyIndex"
::= { win32GroupEntry 1 }

win32GroupDomain OBJECT-TYPE
   SYNTAX         String
   ACCESS         read-write
   STATUS         mandatory
   DESCRIPTION    "The Domain property indicates the name of the Windows NT domain to which a group belongs.<P>Example: NA-SALES"
   REFERENCE      "Win32_Group.Domain"
::= { win32GroupEntry 2 }

win32GroupName OBJECT-TYPE
   SYNTAX         String
   ACCESS         read-write
   STATUS         mandatory
   DESCRIPTION    "The Name property indicates the name of the Win32 local group."
   REFERENCE      "Win32_Group.Name"
::= { win32GroupEntry 3 }

win32GroupStatus OBJECT-TYPE
   SYNTAX         String
   ACCESS         read-write
   STATUS         mandatory
   DESCRIPTION    "The Status property is a string indicating the current status of the object. Various operational and non-operational statuses can be defined. Operational statuses are OK, Degraded and Pred Fail. Pred Fail indicates that an element may be functioning properly but predicting a failure in the near future. An example is a SMART-enabled hard drive. Non-operational statuses can also be specified. These are Error, Starting, Stopping and Service. The latter, Service, could apply during mirror-resilvering of a disk, reload of a user permissions list, or other administrative work. Not all such work is on-line, yet the managed element is neither OK nor in one of the other states."
   REFERENCE      "Win32_Group.Status"
::= { win32GroupEntry 4 }

win32UserAccountTable OBJECT-TYPE
   SYNTAX         SEQUENCE OF Win32UserAccountEntry
   ACCESS         not-accessible
   STATUS         mandatory
   DESCRIPTION    "The Win32_UserAccount class represents data about a user that is known to the Win32 system.<P>Example: mvotava"
   REFERENCE      "Win32_UserAccount"
::= { win32WMI 270 }

win32UserAccountEntry OBJECT-TYPE
   SYNTAX         Win32UserAccountEntry
   ACCESS         not-accessible
   STATUS         mandatory
   DESCRIPTION    ""
   INDEX          { win32UserAccountKeyIndex }
::= { win32UserAccountTable 1 }

Win32UserAccountEntry ::= SEQUENCE
{
   win32UserAccountKeyIndex String,
   win32UserAccountAccountType Uint32,
   win32UserAccountDisabled Boolean,
   win32UserAccountDomain String,
   win32UserAccountFullName String,
   win32UserAccountLockout Boolean,
   win32UserAccountName String,
   win32UserAccountPasswordChangeable Boolean,
   win32UserAccountPasswordExpires Boolean,
   win32UserAccountPasswordRequired Boolean,
   win32UserAccountStatus String
}

win32UserAccountKeyIndex OBJECT-TYPE
   SYNTAX         String
   ACCESS         read-write
   STATUS         mandatory
   DESCRIPTION    ""
   REFERENCE      "Win32_UserAccount.KeyIndex"
::= { win32UserAccountEntry 1 }

win32UserAccountAccountType OBJECT-TYPE
   SYNTAX         Uint32
   ACCESS         read-write
   STATUS         mandatory
   DESCRIPTION    "The AccountType property indicates the type of the Win32 user account."
   REFERENCE      "Win32_UserAccount.AccountType"
::= { win32UserAccountEntry 2 }

win32UserAccountDisabled OBJECT-TYPE
   SYNTAX         Boolean
   ACCESS         read-write
   STATUS         mandatory
   DESCRIPTION    "The Disabled property determines whether the Win32 user account is disabled.<P>Values: TRUE or FALSE. If TRUE, the user account is disabled."
   REFERENCE      "Win32_UserAccount.Disabled"
::= { win32UserAccountEntry 3 }

win32UserAccountDomain OBJECT-TYPE
   SYNTAX         String
   ACCESS         read-write
   STATUS         mandatory
   DESCRIPTION    "The Domain property indicates the name of the Windows NT domain to which a user belongs.<P>Example: NA-SALES"
   REFERENCE      "Win32_UserAccount.Domain"
::= { win32UserAccountEntry 4 }

win32UserAccountFullName OBJECT-TYPE
   SYNTAX         String
   ACCESS         read-write
   STATUS         mandatory
   DESCRIPTION    "The FullName property indicates the full name of the local user.<P>Example: Thomas Williams"
   REFERENCE      "Win32_UserAccount.FullName"
::= { win32UserAccountEntry 5 }

win32UserAccountLockout OBJECT-TYPE
   SYNTAX         Boolean
   ACCESS         read-write
   STATUS         mandatory
   DESCRIPTION    "The Lockout property determines whether the user account is locked out of the Win32 system.<P>Values: TRUE or FALSE. If TRUE, the user account is locked out."
   REFERENCE      "Win32_UserAccount.Lockout"
::= { win32UserAccountEntry 6 }

win32UserAccountName OBJECT-TYPE
   SYNTAX         String
   ACCESS         read-write
   STATUS         mandatory
   DESCRIPTION    "The Name property indicates the network name of the local user.<P>Example: thomasw"
   REFERENCE      "Win32_UserAccount.Name"
::= { win32UserAccountEntry 7 }

win32UserAccountPasswordChangeable OBJECT-TYPE
   SYNTAX         Boolean
   ACCESS         read-write
   STATUS         mandatory
   DESCRIPTION    "The PasswordChangeable property determines whether the password on the Win32 user account can be changed.<P>Values: TRUE or FALSE. If TRUE, the password can be changed."
   REFERENCE      "Win32_UserAccount.PasswordChangeable"
::= { win32UserAccountEntry 8 }

win32UserAccountPasswordExpires OBJECT-TYPE
   SYNTAX         Boolean
   ACCESS         read-write
   STATUS         mandatory
   DESCRIPTION    "The PasswordExpires property determines whether the password on the Win32 user account will expire.<P>Values: TRUE or FALSE. If TRUE, the password will expire."
   REFERENCE      "Win32_UserAccount.PasswordExpires"
::= { win32UserAccountEntry 9 }

win32UserAccountPasswordRequired OBJECT-TYPE
   SYNTAX         Boolean
   ACCESS         read-write
   STATUS         mandatory
   DESCRIPTION    "The PasswordRequired property determines whether a password is required on the Win32 user account.<P>Values: TRUE or FALSE. If TRUE, a password is required."
   REFERENCE      "Win32_UserAccount.PasswordRequired"
::= { win32UserAccountEntry 10 }

win32UserAccountStatus OBJECT-TYPE
   SYNTAX         String
   ACCESS         read-write
   STATUS         mandatory
   DESCRIPTION    "The Status property is a string indicating the current status of the object. Various operational and non-operational statuses can be defined. Operational statuses are OK, Degraded and Pred Fail. Pred Fail indicates that an element may be functioning properly but predicting a failure in the near future. An example is a SMART-enabled hard drive. Non-operational statuses can also be specified. These are Error, Starting, Stopping and Service. The latter, Service, could apply during mirror-resilvering of a disk, reload of a user permissions list, or other administrative work. Not all such work is on-line, yet the managed element is neither OK nor in one of the other states."
   REFERENCE      "Win32_UserAccount.Status"
::= { win32UserAccountEntry 11 }

win32NetworkConnectionTable OBJECT-TYPE
   SYNTAX         SEQUENCE OF Win32NetworkConnectionEntry
   ACCESS         not-accessible
   STATUS         mandatory
   DESCRIPTION    "The Win32_NetworkConnection class represents a network connection in a Win32 environment.<P>Example: Any network connection"
   REFERENCE      "Win32_NetworkConnection"
::= { win32WMI 280 }

win32NetworkConnectionEntry OBJECT-TYPE
   SYNTAX         Win32NetworkConnectionEntry
   ACCESS         not-accessible
   STATUS         mandatory
   DESCRIPTION    ""
   INDEX          { win32NetworkConnectionKeyIndex }
::= { win32NetworkConnectionTable 1 }

Win32NetworkConnectionEntry ::= SEQUENCE
{
   win32NetworkConnectionKeyIndex String,
   win32NetworkConnectionComment String,
   win32NetworkConnectionConnectionType String,
   win32NetworkConnectionDisplayType String,
   win32NetworkConnectionLocalName String,
   win32NetworkConnectionName String,
   win32NetworkConnectionPersistent Boolean,
   win32NetworkConnectionProviderName String,
   win32NetworkConnectionRemoteName String,
   win32NetworkConnectionRemotePath String,
   win32NetworkConnectionResourceType String,
   win32NetworkConnectionUserName String,
   win32NetworkConnectionStatus String
}

win32NetworkConnectionKeyIndex OBJECT-TYPE
   SYNTAX         String
   ACCESS         read-write
   STATUS         mandatory
   DESCRIPTION    ""
   REFERENCE      "Win32_NetworkConnection.KeyIndex"
::= { win32NetworkConnectionEntry 1 }

win32NetworkConnectionComment OBJECT-TYPE
   SYNTAX         String
   ACCESS         read-write
   STATUS         mandatory
   DESCRIPTION    "The Comment property indicates a textual comment about the network connection.<P>Example: A comment might look like this."
   REFERENCE      "Win32_NetworkConnection.Comment"
::= { win32NetworkConnectionEntry 2 }

win32NetworkConnectionConnectionType OBJECT-TYPE
   SYNTAX         String
   ACCESS         read-write
   STATUS         mandatory
   DESCRIPTION    "The ConnectionType property indicates the connection type of the network connection.<P>Example: Permanent"
   REFERENCE      "Win32_NetworkConnection.ConnectionType"
::= { win32NetworkConnectionEntry 3 }

win32NetworkConnectionDisplayType OBJECT-TYPE
   SYNTAX         String
   ACCESS         read-write
   STATUS         mandatory
   DESCRIPTION    "The DisplayType property indicates the display type of the network connection.<P>Example: Generic"
   REFERENCE      "Win32_NetworkConnection.DisplayType"
::= { win32NetworkConnectionEntry 4 }

win32NetworkConnectionLocalName OBJECT-TYPE
   SYNTAX         String
   ACCESS         read-write
   STATUS         mandatory
   DESCRIPTION    "The LocalName property indicates the local name of the network connection.<P>Example: c:\\public"
   REFERENCE      "Win32_NetworkConnection.LocalName"
::= { win32NetworkConnectionEntry 5 }

win32NetworkConnectionName OBJECT-TYPE
   SYNTAX         String
   ACCESS         read-write
   STATUS         mandatory
   DESCRIPTION    "The Name property indicates the name of the current network connection.<P>Example: \\\\NTRELEASE\\NTLOGON"
   REFERENCE      "Win32_NetworkConnection.Name"
::= { win32NetworkConnectionEntry 6 }

win32NetworkConnectionPersistent OBJECT-TYPE
   SYNTAX         Boolean
   ACCESS         read-write
   STATUS         mandatory
   DESCRIPTION    "The Persistent property determines whether this connection will be reconnected automatically by the operating system on the next logon.<P>Values: TRUE or FALSE. If TRUE, the network connection will be automatically connected."
   REFERENCE      "Win32_NetworkConnection.Persistent"
::= { win32NetworkConnectionEntry 7 }

win32NetworkConnectionProviderName OBJECT-TYPE
   SYNTAX         String
   ACCESS         read-write
   STATUS         mandatory
   DESCRIPTION    "The ProviderName property indicates the provider name of the network connection.<P>Example: Microsoft Windows Network"
   REFERENCE      "Win32_NetworkConnection.ProviderName"
::= { win32NetworkConnectionEntry 8 }

win32NetworkConnectionRemoteName OBJECT-TYPE
   SYNTAX         String
   ACCESS         read-write
   STATUS         mandatory
   DESCRIPTION    "The RemoteName property indicates the remote name of the network connection.<P>Example: \\\\NTRELEASE\\IPC$"
   REFERENCE      "Win32_NetworkConnection.RemoteName"
::= { win32NetworkConnectionEntry 9 }

win32NetworkConnectionRemotePath OBJECT-TYPE
   SYNTAX         String
   ACCESS         read-write
   STATUS         mandatory
   DESCRIPTION    "The RemotePath property indicates the remote path to the network connection.<P>Example: \\\\infosrv1\\public"
   REFERENCE      "Win32_NetworkConnection.RemotePath"
::= { win32NetworkConnectionEntry 10 }

win32NetworkConnectionResourceType OBJECT-TYPE
   SYNTAX         String
   ACCESS         read-write
   STATUS         mandatory
   DESCRIPTION    "The ResourceType property indicates the resource type of the network connection.<P>Example: CDROM"
   REFERENCE      "Win32_NetworkConnection.ResourceType"
::= { win32NetworkConnectionEntry 11 }

win32NetworkConnectionUserName OBJECT-TYPE
   SYNTAX         String
   ACCESS         read-write
   STATUS         mandatory
   DESCRIPTION    "The UserName property indicates the user name of the network connection.<P>Example: SYSTEM"
   REFERENCE      "Win32_NetworkConnection.UserName"
::= { win32NetworkConnectionEntry 12 }

win32NetworkConnectionStatus OBJECT-TYPE
   SYNTAX         String
   ACCESS         read-write
   STATUS         mandatory
   DESCRIPTION    "The Status property is a string indicating the current status of the object. Various operational and non-operational statuses can be defined. Operational statuses are OK, Degraded and Pred Fail. Pred Fail indicates that an element may be functioning properly but predicting a failure in the near future. An example is a SMART-enabled hard drive. Non-operational statuses can also be specified. These are Error, Starting, Stopping and Service. The latter, Service, could apply during mirror-resilvering of a disk, reload of a user permissions list, or other administrative work. Not all such work is on-line, yet the managed element is neither OK nor in one of the other states."
   REFERENCE      "Win32_NetworkConnection.Status"
::= { win32NetworkConnectionEntry 13 }

win32DeviceMemoryAddressTable OBJECT-TYPE
   SYNTAX         SEQUENCE OF Win32DeviceMemoryAddressEntry
   ACCESS         not-accessible
   STATUS         mandatory
   DESCRIPTION    "The Win32_DeviceMemoryAddress class represents a device memory address on a Win32 system.<P>Example: ScsiPort0 device memory address"
   REFERENCE      "Win32_DeviceMemoryAddress"
::= { win32WMI 290 }

win32DeviceMemoryAddressEntry OBJECT-TYPE
   SYNTAX         Win32DeviceMemoryAddressEntry
   ACCESS         not-accessible
   STATUS         mandatory
   DESCRIPTION    ""
   INDEX          { win32DeviceMemoryAddressKeyIndex }
::= { win32DeviceMemoryAddressTable 1 }

Win32DeviceMemoryAddressEntry ::= SEQUENCE
{
   win32DeviceMemoryAddressKeyIndex String,
   win32DeviceMemoryAddressMemoryType String,
   win32DeviceMemoryAddressStatus String
}

win32DeviceMemoryAddressKeyIndex OBJECT-TYPE
   SYNTAX         String
   ACCESS         read-write
   STATUS         mandatory
   DESCRIPTION    ""
   REFERENCE      "Win32_DeviceMemoryAddress.KeyIndex"
::= { win32DeviceMemoryAddressEntry 1 }

win32DeviceMemoryAddressMemoryType OBJECT-TYPE
   SYNTAX         String
   ACCESS         read-write
   STATUS         mandatory
   DESCRIPTION    "The MemoryType property indicates the memory type of the Win32 system memory resource.<P>Example: PCI"
   REFERENCE      "Win32_DeviceMemoryAddress.MemoryType"
::= { win32DeviceMemoryAddressEntry 2 }

win32DeviceMemoryAddressStatus OBJECT-TYPE
   SYNTAX         String
   ACCESS         read-write
   STATUS         mandatory
   DESCRIPTION    "The Status property is a string indicating the current status of the object. Various operational and non-operational statuses can be defined. Operational statuses are OK, Degraded and Pred Fail. Pred Fail indicates that an element may be functioning properly but predicting a failure in the near future. An example is a SMART-enabled hard drive. Non-operational statuses can also be specified. These are Error, Starting, Stopping and Service. The latter, Service, could apply during mirror-resilvering of a disk, reload of a user permissions list, or other administrative work. Not all such work is on-line, yet the managed element is neither OK nor in one of the other states."
   REFERENCE      "Win32_DeviceMemoryAddress.Status"
::= { win32DeviceMemoryAddressEntry 3 }

win32PortResourceTable OBJECT-TYPE
   SYNTAX         SEQUENCE OF Win32PortResourceEntry
   ACCESS         not-accessible
   STATUS         mandatory
   DESCRIPTION    "The Win32_PortResource class represents a port number on a Win32 system."
   REFERENCE      "Win32_PortResource"
::= { win32WMI 300 }

win32PortResourceEntry OBJECT-TYPE
   SYNTAX         Win32PortResourceEntry
   ACCESS         not-accessible
   STATUS         mandatory
   DESCRIPTION    ""
   INDEX          { win32PortResourceKeyIndex }
::= { win32PortResourceTable 1 }

Win32PortResourceEntry ::= SEQUENCE
{
   win32PortResourceKeyIndex String,
   win32PortResourceAlias Boolean,
   win32PortResourceStatus String
}

win32PortResourceKeyIndex OBJECT-TYPE
   SYNTAX         String
   ACCESS         read-write
   STATUS         mandatory
   DESCRIPTION    ""
   REFERENCE      "Win32_PortResource.KeyIndex"
::= { win32PortResourceEntry 1 }

win32PortResourceAlias OBJECT-TYPE
   SYNTAX         Boolean
   ACCESS         read-write
   STATUS         mandatory
   DESCRIPTION    "The Alias property indicates whether this instance of the class represents the base port address, or one of the aliased ranges.<P>Values: TRUE or FALSE. If TRUE, this instance represents the base port address."
   REFERENCE      "Win32_PortResource.Alias"
::= { win32PortResourceEntry 2 }

win32PortResourceStatus OBJECT-TYPE
   SYNTAX         String
   ACCESS         read-write
   STATUS         mandatory
   DESCRIPTION    "The Status property is a string indicating the current status of the object. Various operational and non-operational statuses can be defined. Operational statuses are OK, Degraded and Pred Fail. Pred Fail indicates that an element may be functioning properly but predicting a failure in the near future. An example is a SMART-enabled hard drive. Non-operational statuses can also be specified. These are Error, Starting, Stopping and Service. The latter, Service, could apply during mirror-resilvering of a disk, reload of a user permissions list, or other administrative work. Not all such work is on-line, yet the managed element is neither OK nor in one of the other states."
   REFERENCE      "Win32_PortResource.Status"
::= { win32PortResourceEntry 3 }

win32DMAChannelTable OBJECT-TYPE
   SYNTAX         SEQUENCE OF Win32DMAChannelEntry
   ACCESS         not-accessible
   STATUS         mandatory
   DESCRIPTION    "The Win32_DMAChannel class represents a direct memory access (DMA) channel on a Win32 system."
   REFERENCE      "Win32_DMAChannel"
::= { win32WMI 310 }

win32DMAChannelEntry OBJECT-TYPE
   SYNTAX         Win32DMAChannelEntry
   ACCESS         not-accessible
   STATUS         mandatory
   DESCRIPTION    ""
   INDEX          { win32DMAChannelKeyIndex }
::= { win32DMAChannelTable 1 }

Win32DMAChannelEntry ::= SEQUENCE
{
   win32DMAChannelKeyIndex String,
   win32DMAChannelPort Uint32,
   win32DMAChannelStatus String
}

win32DMAChannelKeyIndex OBJECT-TYPE
   SYNTAX         String
   ACCESS         read-write
   STATUS         mandatory
   DESCRIPTION    ""
   REFERENCE      "Win32_DMAChannel.KeyIndex"
::= { win32DMAChannelEntry 1 }

win32DMAChannelPort OBJECT-TYPE
   SYNTAX         Uint32
   ACCESS         read-write
   STATUS         mandatory
   DESCRIPTION    "The Port property indicates the port number of the Win32 DMA channel.<P>Example: 12"
   REFERENCE      "Win32_DMAChannel.Port"
::= { win32DMAChannelEntry 2 }

win32DMAChannelStatus OBJECT-TYPE
   SYNTAX         String
   ACCESS         read-write
   STATUS         mandatory
   DESCRIPTION    "The Status property is a string indicating the current status of the object. Various operational and non-operational statuses can be defined. Operational statuses are OK, Degraded and Pred Fail. Pred Fail indicates that an element may be functioning properly but predicting a failure in the near future. An example is a SMART-enabled hard drive. Non-operational statuses can also be specified. These are Error, Starting, Stopping and Service. The latter, Service, could apply during mirror-resilvering of a disk, reload of a user permissions list, or other administrative work. Not all such work is on-line, yet the managed element is neither OK nor in one of the other states."
   REFERENCE      "Win32_DMAChannel.Status"
::= { win32DMAChannelEntry 3 }

win32EnvironmentTable OBJECT-TYPE
   SYNTAX         SEQUENCE OF Win32EnvironmentEntry
   ACCESS         not-accessible
   STATUS         mandatory
   DESCRIPTION    "The Win32_Environment class represents an environment or system environment on a Win32 system.<P>Example: COMPUTERNAME"
   REFERENCE      "Win32_Environment"
::= { win32WMI 320 }

win32EnvironmentEntry OBJECT-TYPE
   SYNTAX         Win32EnvironmentEntry
   ACCESS         not-accessible
   STATUS         mandatory
   DESCRIPTION    ""
   INDEX          { win32EnvironmentKeyIndex }
::= { win32EnvironmentTable 1 }

Win32EnvironmentEntry ::= SEQUENCE
{
   win32EnvironmentKeyIndex String,
   win32EnvironmentName String,
   win32EnvironmentSystemVariable Boolean,
   win32EnvironmentUserName String,
   win32EnvironmentVariableValue String,
   win32EnvironmentStatus String
}

win32EnvironmentKeyIndex OBJECT-TYPE
   SYNTAX         String
   ACCESS         read-write
   STATUS         mandatory
   DESCRIPTION    ""
   REFERENCE      "Win32_Environment.KeyIndex"
::= { win32EnvironmentEntry 1 }

win32EnvironmentName OBJECT-TYPE
   SYNTAX         String
   ACCESS         read-write
   STATUS         mandatory
   DESCRIPTION    "The Name property indicates the name of a Win32 environment variable.<P>Example: Path"
   REFERENCE      "Win32_Environment.Name"
::= { win32EnvironmentEntry 2 }

win32EnvironmentSystemVariable OBJECT-TYPE
   SYNTAX         Boolean
   ACCESS         read-write
   STATUS         mandatory
   DESCRIPTION    "The SystemVariable property determines whether the variable is a system variable<P>Values: TRUE or FALSE. If TRUE, the variable is a system variable."
   REFERENCE      "Win32_Environment.SystemVariable"
::= { win32EnvironmentEntry 3 }

win32EnvironmentUserName OBJECT-TYPE
   SYNTAX         String
   ACCESS         read-write
   STATUS         mandatory
   DESCRIPTION    "The UserName property indicates the user name of a Win32 environment.<P>Example: COMPUTERNAME"
   REFERENCE      "Win32_Environment.UserName"
::= { win32EnvironmentEntry 4 }

win32EnvironmentVariableValue OBJECT-TYPE
   SYNTAX         String
   ACCESS         read-write
   STATUS         mandatory
   DESCRIPTION    "The VariableValue property indicates the value of a Win32 environment variable."
   REFERENCE      "Win32_Environment.VariableValue"
::= { win32EnvironmentEntry 5 }

win32EnvironmentStatus OBJECT-TYPE
   SYNTAX         String
   ACCESS         read-write
   STATUS         mandatory
   DESCRIPTION    "The Status property is a string indicating the current status of the object. Various operational and non-operational statuses can be defined. Operational statuses are OK, Degraded and Pred Fail. Pred Fail indicates that an element may be functioning properly but predicting a failure in the near future. An example is a SMART-enabled hard drive. Non-operational statuses can also be specified. These are Error, Starting, Stopping and Service. The latter, Service, could apply during mirror-resilvering of a disk, reload of a user permissions list, or other administrative work. Not all such work is on-line, yet the managed element is neither OK nor in one of the other states."
   REFERENCE      "Win32_Environment.Status"
::= { win32EnvironmentEntry 6 }

win32IRQResourceTable OBJECT-TYPE
   SYNTAX         SEQUENCE OF Win32IRQResourceEntry
   ACCESS         not-accessible
   STATUS         mandatory
   DESCRIPTION    "The Win32_IRQResource class represents an interrupt request line (IRQ) number on a Win32 system.<P>Example: IRQ 5"
   REFERENCE      "Win32_IRQResource"
::= { win32WMI 330 }

win32IRQResourceEntry OBJECT-TYPE
   SYNTAX         Win32IRQResourceEntry
   ACCESS         not-accessible
   STATUS         mandatory
   DESCRIPTION    ""
   INDEX          { win32IRQResourceKeyIndex }
::= { win32IRQResourceTable 1 }

Win32IRQResourceEntry ::= SEQUENCE
{
   win32IRQResourceKeyIndex String,
   win32IRQResourceVector Uint32,
   win32IRQResourceHardware Boolean,
   win32IRQResourceStatus String
}

win32IRQResourceKeyIndex OBJECT-TYPE
   SYNTAX         String
   ACCESS         read-write
   STATUS         mandatory
   DESCRIPTION    ""
   REFERENCE      "Win32_IRQResource.KeyIndex"
::= { win32IRQResourceEntry 1 }

win32IRQResourceVector OBJECT-TYPE
   SYNTAX         Uint32
   ACCESS         read-write
   STATUS         mandatory
   DESCRIPTION    "The Vector property indicates the vector of the Win32 IRQ resource.<P>Example:53"
   REFERENCE      "Win32_IRQResource.Vector"
::= { win32IRQResourceEntry 2 }

win32IRQResourceHardware OBJECT-TYPE
   SYNTAX         Boolean
   ACCESS         read-write
   STATUS         mandatory
   DESCRIPTION    "Indicates whether IRQ is a hardware or software IRQ."
   REFERENCE      "Win32_IRQResource.Hardware"
::= { win32IRQResourceEntry 3 }

win32IRQResourceStatus OBJECT-TYPE
   SYNTAX         String
   ACCESS         read-write
   STATUS         mandatory
   DESCRIPTION    "The Status property is a string indicating the current status of the object. Various operational and non-operational statuses can be defined. Operational statuses are OK, Degraded and Pred Fail. Pred Fail indicates that an element may be functioning properly but predicting a failure in the near future. An example is a SMART-enabled hard drive. Non-operational statuses can also be specified. These are Error, Starting, Stopping and Service. The latter, Service, could apply during mirror-resilvering of a disk, reload of a user permissions list, or other administrative work. Not all such work is on-line, yet the managed element is neither OK nor in one of the other states."
   REFERENCE      "Win32_IRQResource.Status"
::= { win32IRQResourceEntry 4 }

win32LoadOrderGroupTable OBJECT-TYPE
   SYNTAX         SEQUENCE OF Win32LoadOrderGroupEntry
   ACCESS         not-accessible
   STATUS         mandatory
   DESCRIPTION    "The Win32_LoadOrderGroup class represents a grouping of system services defining execution dependencies. The services must be initiated in the order specified by the Load Order Group as the services are dependent on each other. These dependent services require the presence of the antecedent services in order to function correctly."
   REFERENCE      "Win32_LoadOrderGroup"
::= { win32WMI 340 }

win32LoadOrderGroupEntry OBJECT-TYPE
   SYNTAX         Win32LoadOrderGroupEntry
   ACCESS         not-accessible
   STATUS         mandatory
   DESCRIPTION    ""
   INDEX          { win32LoadOrderGroupKeyIndex }
::= { win32LoadOrderGroupTable 1 }

Win32LoadOrderGroupEntry ::= SEQUENCE
{
   win32LoadOrderGroupKeyIndex String,
   win32LoadOrderGroupGroupOrder Uint32,
   win32LoadOrderGroupName String,
   win32LoadOrderGroupDriverEnabled Boolean,
   win32LoadOrderGroupStatus String
}

win32LoadOrderGroupKeyIndex OBJECT-TYPE
   SYNTAX         String
   ACCESS         read-write
   STATUS         mandatory
   DESCRIPTION    ""
   REFERENCE      "Win32_LoadOrderGroup.KeyIndex"
::= { win32LoadOrderGroupEntry 1 }

win32LoadOrderGroupGroupOrder OBJECT-TYPE
   SYNTAX         Uint32
   ACCESS         read-write
   STATUS         mandatory
   DESCRIPTION    "The GroupOrder property indicates the group order.<P>Example: 2"
   REFERENCE      "Win32_LoadOrderGroup.GroupOrder"
::= { win32LoadOrderGroupEntry 2 }

win32LoadOrderGroupName OBJECT-TYPE
   SYNTAX         String
   ACCESS         read-write
   STATUS         mandatory
   DESCRIPTION    "The Name property indicates the name of the load order group."
   REFERENCE      "Win32_LoadOrderGroup.Name"
::= { win32LoadOrderGroupEntry 3 }

win32LoadOrderGroupDriverEnabled OBJECT-TYPE
   SYNTAX         Boolean
   ACCESS         read-write
   STATUS         mandatory
   DESCRIPTION    "The DriverEnabled property indicates whether this LoadOrderGroup can contain drivers."
   REFERENCE      "Win32_LoadOrderGroup.DriverEnabled"
::= { win32LoadOrderGroupEntry 4 }

win32LoadOrderGroupStatus OBJECT-TYPE
   SYNTAX         String
   ACCESS         read-write
   STATUS         mandatory
   DESCRIPTION    "The Status property is a string indicating the current status of the object. Various operational and non-operational statuses can be defined. Operational statuses are OK, Degraded and Pred Fail. Pred Fail indicates that an element may be functioning properly but predicting a failure in the near future. An example is a SMART-enabled hard drive. Non-operational statuses can also be specified. These are Error, Starting, Stopping and Service. The latter, Service, could apply during mirror-resilvering of a disk, reload of a user permissions list, or other administrative work. Not all such work is on-line, yet the managed element is neither OK nor in one of the other states."
   REFERENCE      "Win32_LoadOrderGroup.Status"
::= { win32LoadOrderGroupEntry 5 }

win32NetworkClientTable OBJECT-TYPE
   SYNTAX         SEQUENCE OF Win32NetworkClientEntry
   ACCESS         not-accessible
   STATUS         mandatory
   DESCRIPTION    "The Win32_NetworkClient class represents a network client computer on a network.<P>Membership Criteria: Any computer system on the network with a client relationship to the system is a descendent (or member) of this class.<P>Example: A computer running Windows NT workstation or Windows 95 that is part of a Windows NT domain"
   REFERENCE      "Win32_NetworkClient"
::= { win32WMI 350 }

win32NetworkClientEntry OBJECT-TYPE
   SYNTAX         Win32NetworkClientEntry
   ACCESS         not-accessible
   STATUS         mandatory
   DESCRIPTION    ""
   INDEX          { win32NetworkClientKeyIndex }
::= { win32NetworkClientTable 1 }

Win32NetworkClientEntry ::= SEQUENCE
{
   win32NetworkClientKeyIndex String,
   win32NetworkClientManufacturer String,
   win32NetworkClientName String,
   win32NetworkClientStatus String
}

win32NetworkClientKeyIndex OBJECT-TYPE
   SYNTAX         String
   ACCESS         read-write
   STATUS         mandatory
   DESCRIPTION    ""
   REFERENCE      "Win32_NetworkClient.KeyIndex"
::= { win32NetworkClientEntry 1 }

win32NetworkClientManufacturer OBJECT-TYPE
   SYNTAX         String
   ACCESS         read-write
   STATUS         mandatory
   DESCRIPTION    "The Manufacturer property indicates the name of the manufacturer of the network client running on a Win32 system.<P>Example: Compaq"
   REFERENCE      "Win32_NetworkClient.Manufacturer"
::= { win32NetworkClientEntry 2 }

win32NetworkClientName OBJECT-TYPE
   SYNTAX         String
   ACCESS         read-write
   STATUS         mandatory
   DESCRIPTION    "The Name property identifies the name of the network client running on a Win32 system.<P>Example: Funazonki"
   REFERENCE      "Win32_NetworkClient.Name"
::= { win32NetworkClientEntry 3 }

win32NetworkClientStatus OBJECT-TYPE
   SYNTAX         String
   ACCESS         read-write
   STATUS         mandatory
   DESCRIPTION    "The Status property is a string indicating the current status of the object. Various operational and non-operational statuses can be defined. Operational statuses are OK, Degraded and Pred Fail. Pred Fail indicates that an element may be functioning properly but predicting a failure in the near future. An example is a SMART-enabled hard drive. Non-operational statuses can also be specified. These are Error, Starting, Stopping and Service. The latter, Service, could apply during mirror-resilvering of a disk, reload of a user permissions list, or other administrative work. Not all such work is on-line, yet the managed element is neither OK nor in one of the other states."
   REFERENCE      "Win32_NetworkClient.Status"
::= { win32NetworkClientEntry 4 }

win32ShareTable OBJECT-TYPE
   SYNTAX         SEQUENCE OF Win32ShareEntry
   ACCESS         not-accessible
   STATUS         mandatory
   DESCRIPTION    ""
   REFERENCE      "Win32_Share"
::= { win32WMI 360 }

win32ShareEntry OBJECT-TYPE
   SYNTAX         Win32ShareEntry
   ACCESS         not-accessible
   STATUS         mandatory
   DESCRIPTION    ""
   INDEX          { win32ShareKeyIndex }
::= { win32ShareTable 1 }

Win32ShareEntry ::= SEQUENCE
{
   win32ShareKeyIndex String,
   win32ShareAllowMaximum Boolean,
   win32ShareMaximumAllowed Uint32,
   win32ShareName String,
   win32SharePath String,
   win32ShareType Uint32,
   win32ShareStatus String
}

win32ShareKeyIndex OBJECT-TYPE
   SYNTAX         String
   ACCESS         read-write
   STATUS         mandatory
   DESCRIPTION    ""
   REFERENCE      "Win32_Share.KeyIndex"
::= { win32ShareEntry 1 }

win32ShareAllowMaximum OBJECT-TYPE
   SYNTAX         Boolean
   ACCESS         read-write
   STATUS         mandatory
   DESCRIPTION    ""
   REFERENCE      "Win32_Share.AllowMaximum"
::= { win32ShareEntry 2 }

win32ShareMaximumAllowed OBJECT-TYPE
   SYNTAX         Uint32
   ACCESS         read-write
   STATUS         mandatory
   DESCRIPTION    ""
   REFERENCE      "Win32_Share.MaximumAllowed"
::= { win32ShareEntry 3 }

win32ShareName OBJECT-TYPE
   SYNTAX         String
   ACCESS         read-write
   STATUS         mandatory
   DESCRIPTION    ""
   REFERENCE      "Win32_Share.Name"
::= { win32ShareEntry 4 }

win32SharePath OBJECT-TYPE
   SYNTAX         String
   ACCESS         read-write
   STATUS         mandatory
   DESCRIPTION    ""
   REFERENCE      "Win32_Share.Path"
::= { win32ShareEntry 5 }

win32ShareType OBJECT-TYPE
   SYNTAX         Uint32
   ACCESS         read-write
   STATUS         mandatory
   DESCRIPTION    ""
   REFERENCE      "Win32_Share.Type"
::= { win32ShareEntry 6 }

win32ShareStatus OBJECT-TYPE
   SYNTAX         String
   ACCESS         read-write
   STATUS         mandatory
   DESCRIPTION    "The Status property is a string indicating the current status of the object. Various operational and non-operational statuses can be defined. Operational statuses are OK, Degraded and Pred Fail. Pred Fail indicates that an element may be functioning properly but predicting a failure in the near future. An example is a SMART-enabled hard drive. Non-operational statuses can also be specified. These are Error, Starting, Stopping and Service. The latter, Service, could apply during mirror-resilvering of a disk, reload of a user permissions list, or other administrative work. Not all such work is on-line, yet the managed element is neither OK nor in one of the other states."
   REFERENCE      "Win32_Share.Status"
::= { win32ShareEntry 7 }

win32RegistryTable OBJECT-TYPE
   SYNTAX         SEQUENCE OF Win32RegistryEntry
   ACCESS         not-accessible
   STATUS         mandatory
   DESCRIPTION    ""
   REFERENCE      "Win32_Registry"
::= { win32WMI 370 }

win32RegistryEntry OBJECT-TYPE
   SYNTAX         Win32RegistryEntry
   ACCESS         not-accessible
   STATUS         mandatory
   DESCRIPTION    ""
   INDEX          { win32RegistryKeyIndex }
::= { win32RegistryTable 1 }

Win32RegistryEntry ::= SEQUENCE
{
   win32RegistryKeyIndex String,
   win32RegistryCurrentSize Uint32,
   win32RegistryProposedSize Uint32,
   win32RegistryMaximumSize Uint32,
   win32RegistryName String,
   win32RegistryStatus String
}

win32RegistryKeyIndex OBJECT-TYPE
   SYNTAX         String
   ACCESS         read-write
   STATUS         mandatory
   DESCRIPTION    ""
   REFERENCE      "Win32_Registry.KeyIndex"
::= { win32RegistryEntry 1 }

win32RegistryCurrentSize OBJECT-TYPE
   SYNTAX         Uint32
   ACCESS         read-write
   STATUS         mandatory
   DESCRIPTION    ""
   REFERENCE      "Win32_Registry.CurrentSize"
::= { win32RegistryEntry 2 }

win32RegistryProposedSize OBJECT-TYPE
   SYNTAX         Uint32
   ACCESS         read-write
   STATUS         mandatory
   DESCRIPTION    ""
   REFERENCE      "Win32_Registry.ProposedSize"
::= { win32RegistryEntry 3 }

win32RegistryMaximumSize OBJECT-TYPE
   SYNTAX         Uint32
   ACCESS         read-write
   STATUS         mandatory
   DESCRIPTION    ""
   REFERENCE      "Win32_Registry.MaximumSize"
::= { win32RegistryEntry 4 }

win32RegistryName OBJECT-TYPE
   SYNTAX         String
   ACCESS         read-write
   STATUS         mandatory
   DESCRIPTION    ""
   REFERENCE      "Win32_Registry.Name"
::= { win32RegistryEntry 5 }

win32RegistryStatus OBJECT-TYPE
   SYNTAX         String
   ACCESS         read-write
   STATUS         mandatory
   DESCRIPTION    "The Status property is a string indicating the current status of the object. Various operational and non-operational statuses can be defined. Operational statuses are OK, Degraded and Pred Fail. Pred Fail indicates that an element may be functioning properly but predicting a failure in the near future. An example is a SMART-enabled hard drive. Non-operational statuses can also be specified. These are Error, Starting, Stopping and Service. The latter, Service, could apply during mirror-resilvering of a disk, reload of a user permissions list, or other administrative work. Not all such work is on-line, yet the managed element is neither OK nor in one of the other states."
   REFERENCE      "Win32_Registry.Status"
::= { win32RegistryEntry 6 }

win32NetworkProtocolTable OBJECT-TYPE
   SYNTAX         SEQUENCE OF Win32NetworkProtocolEntry
   ACCESS         not-accessible
   STATUS         mandatory
   DESCRIPTION    ""
   REFERENCE      "Win32_NetworkProcotol"
::= { win32WMI 380 }

win32NetworkProtocolEntry OBJECT-TYPE
   SYNTAX         Win32NetworkProtocolEntry
   ACCESS         not-accessible
   STATUS         mandatory
   DESCRIPTION    ""
   INDEX          { win32NetworkProtocolKeyIndex }
::= { win32NetworkProtocolTable 1 }

Win32NetworkProtocolEntry ::= SEQUENCE
{
   win32NetworkProtocolKeyIndex String,
   win32NetworkProtocolConnectionlessService Boolean,
   win32NetworkProtocolGuranteesDelivery Boolean,
   win32NetworkProtocolGuranteesSequencing Boolean,
   win32NetworkProtocolMaximumAddressSize Uint32,
   win32NetworkProtocolMaximumMessageSize Uint32,
   win32NetworkProtocolMessageOriented Boolean,
   win32NetworkProtocolMinimumAddressSize Uint32,
   win32NetworkProtocolName String,
   win32NetworkProtocolPseudoStreamOriented Boolean,
   win32NetworkProtocolSupportsBroadcasting Boolean,
   win32NetworkProtocolSupportsConnectData Boolean,
   win32NetworkProtocolSupportsDisconnectData Boolean,
   win32NetworkProtocolSupportsEncryption Boolean,
   win32NetworkProtocolSupportsExpiditeData Boolean,
   win32NetworkProtocolSupportsFragmentation Boolean,
   win32NetworkProtocolSupportsGracefulClosing Boolean,
   win32NetworkProtocolSupportsGuaranteedBandwidth Boolean,
   win32NetworkProtocolSupportsMulticasting Boolean,
   win32NetworkProtocolStatus String
}

win32NetworkProtocolKeyIndex OBJECT-TYPE
   SYNTAX         String
   ACCESS         read-write
   STATUS         mandatory
   DESCRIPTION    ""
   REFERENCE      "Win32_NetworkProtocol.KeyIndex"
::= { win32NetworkProtocolEntry 1 }

win32NetworkProtocolConnectionlessService OBJECT-TYPE
   SYNTAX         Boolean
   ACCESS         read-write
   STATUS         mandatory
   DESCRIPTION    ""
   REFERENCE      "Win32_NetworkProtocol.ConnectionlessService"
::= { win32NetworkProtocolEntry 2 }

win32NetworkProtocolGuranteesDelivery OBJECT-TYPE
   SYNTAX         Boolean
   ACCESS         read-write
   STATUS         mandatory
   DESCRIPTION    ""
   REFERENCE      "Win32_NetworkProtocol.GuranteesDelivery"
::= { win32NetworkProtocolEntry 3 }

win32NetworkProtocolGuranteesSequencing OBJECT-TYPE
   SYNTAX         Boolean
   ACCESS         read-write
   STATUS         mandatory
   DESCRIPTION    ""
   REFERENCE      "Win32_NetworkProtocol.GuranteesSequencing"
::= { win32NetworkProtocolEntry 4 }

win32NetworkProtocolMaximumAddressSize OBJECT-TYPE
   SYNTAX         Uint32
   ACCESS         read-write
   STATUS         mandatory
   DESCRIPTION    ""
   REFERENCE      "Win32_NetworkProtocol.MaximumAddressSize"
::= { win32NetworkProtocolEntry 5 }

win32NetworkProtocolMaximumMessageSize OBJECT-TYPE
   SYNTAX         Uint32
   ACCESS         read-write
   STATUS         mandatory
   DESCRIPTION    ""
   REFERENCE      "Win32_NetworkProtocol.MaximumMessageSize"
::= { win32NetworkProtocolEntry 6 }

win32NetworkProtocolMessageOriented OBJECT-TYPE
   SYNTAX         Boolean
   ACCESS         read-write
   STATUS         mandatory
   DESCRIPTION    ""
   REFERENCE      "Win32_NetworkProtocol.MessageOriented"
::= { win32NetworkProtocolEntry 7 }

win32NetworkProtocolMinimumAddressSize OBJECT-TYPE
   SYNTAX         Uint32
   ACCESS         read-write
   STATUS         mandatory
   DESCRIPTION    ""
   REFERENCE      "Win32_NetworkProtocol.MinimumAddressSize"
::= { win32NetworkProtocolEntry 8 }

win32NetworkProtocolName OBJECT-TYPE
   SYNTAX         String
   ACCESS         read-write
   STATUS         mandatory
   DESCRIPTION    ""
   REFERENCE      "Win32_NetworkProtocol.Name"
::= { win32NetworkProtocolEntry 9 }

win32NetworkProtocolPseudoStreamOriented OBJECT-TYPE
   SYNTAX         Boolean
   ACCESS         read-write
   STATUS         mandatory
   DESCRIPTION    ""
   REFERENCE      "Win32_NetworkProtocol.PseudoStreamOriented"
::= { win32NetworkProtocolEntry 10 }

win32NetworkProtocolSupportsBroadcasting OBJECT-TYPE
   SYNTAX         Boolean
   ACCESS         read-write
   STATUS         mandatory
   DESCRIPTION    ""
   REFERENCE      "Win32_NetworkProtocol.SupportsBroadcasting"
::= { win32NetworkProtocolEntry 11 }

win32NetworkProtocolSupportsConnectData OBJECT-TYPE
   SYNTAX         Boolean
   ACCESS         read-write
   STATUS         mandatory
   DESCRIPTION    ""
   REFERENCE      "Win32_NetworkProtocol.SupportsConnectData"
::= { win32NetworkProtocolEntry 12 }

win32NetworkProtocolSupportsDisconnectData OBJECT-TYPE
   SYNTAX         Boolean
   ACCESS         read-write
   STATUS         mandatory
   DESCRIPTION    ""
   REFERENCE      "Win32_NetworkProtocol.SupportsDisconnectData"
::= { win32NetworkProtocolEntry 13 }

win32NetworkProtocolSupportsEncryption OBJECT-TYPE
   SYNTAX         Boolean
   ACCESS         read-write
   STATUS         mandatory
   DESCRIPTION    ""
   REFERENCE      "Win32_NetworkProtocol.SupportsEncryption"
::= { win32NetworkProtocolEntry 14}

win32NetworkProtocolSupportsExpiditeData OBJECT-TYPE
   SYNTAX         Boolean
   ACCESS         read-write
   STATUS         mandatory
   DESCRIPTION    ""
   REFERENCE      "Win32_NetworkProtocol.SupportsExiditeData"
::= { win32NetworkProtocolEntry 15 }

win32NetworkProtocolSupportsFragmentation OBJECT-TYPE
   SYNTAX         Boolean
   ACCESS         read-write
   STATUS         mandatory
   DESCRIPTION    ""
   REFERENCE      "Win32_NetworkProtocol.SupportsFragmentation"
::= { win32NetworkProtocolEntry 16 }

win32NetworkProtocolSupportsGracefulClosing OBJECT-TYPE
   SYNTAX         Boolean
   ACCESS         read-write
   STATUS         mandatory
   DESCRIPTION    ""
   REFERENCE      "Win32_NetworkProtocol.SuppportsGracefulClosing"
::= { win32NetworkProtocolEntry 17 }

win32NetworkProtocolSupportsGuaranteedBandwidth OBJECT-TYPE
   SYNTAX         Boolean
   ACCESS         read-write
   STATUS         mandatory
   DESCRIPTION    ""
   REFERENCE      "Win32_NetworkProtocol.SupportsGuaranteedBandwidth"
::= { win32NetworkProtocolEntry 18 }

win32NetworkProtocolSupportsMulticasting OBJECT-TYPE
   SYNTAX         Boolean
   ACCESS         read-write
   STATUS         mandatory
   DESCRIPTION    ""
   REFERENCE      "Win32_NetworkProtocol.SupportsMulticasting"
::= { win32NetworkProtocolEntry 19 }

win32NetworkProtocolStatus OBJECT-TYPE
   SYNTAX         String
   ACCESS         read-write
   STATUS         mandatory
   DESCRIPTION    "The Status property is a string indicating the current status of the object. Various operational and non-operational statuses can be defined. Operational statuses are OK, Degraded and Pred Fail. Pred Fail indicates that an element may be functioning properly but predicting a failure in the near future. An example is a SMART-enabled hard drive. Non-operational statuses can also be specified. These are Error, Starting, Stopping and Service. The latter, Service, could apply during mirror-resilvering of a disk, reload of a user permissions list, or other administrative work. Not all such work is on-line, yet the managed element is neither OK nor in one of the other states."
   REFERENCE      "Win32_NetworkProtocol.Status"
::= { win32NetworkProtocolEntry 20 }

win32ProcessStartupTable OBJECT-TYPE
   SYNTAX         SEQUENCE OF Win32ProcessStartupEntry
   ACCESS         not-accessible
   STATUS         mandatory
   DESCRIPTION    ""
   REFERENCE      "Win32_ProcessStartup"
::= { win32WMI 400 }

win32ProcessStartupEntry OBJECT-TYPE
   SYNTAX         Win32ProcessStartupEntry
   ACCESS         not-accessible
   STATUS         mandatory
   DESCRIPTION    ""
   INDEX          { win32ProcessStartupKeyIndex }
::= { win32ProcessStartupTable 1 }

Win32ProcessStartupEntry ::= SEQUENCE
{
   win32ProcessStartupKeyIndex String,
   win32ProcessStartupCreateFlags Uint32,
   win32ProcessStartupPriorityClass Uint32,
--   win32ProcessStartupEnvironmentVariables String,
   win32ProcessStartupWinstationDesktop String,
   win32ProcessStartupTitle String,
   win32ProcessStartupX Uint32,
   win32ProcessStartupY Uint32,
   win32ProcessStartupXSize Uint32,
   win32ProcessStartupYSize Uint32,
   win32ProcessStartupXCountChars Uint32,
   win32ProcessStartupYCountChars Uint32,
   win32ProcessStartupFillAttribute Uint32,
   win32ProcessStartupShowWindow Uint16,
   win32ProcessStartupErrorMode Uint16,
   win32ProcessStartupStatus String
}

win32ProcessStartupKeyIndex OBJECT-TYPE
   SYNTAX         String
   ACCESS         read-write
   STATUS         mandatory
   DESCRIPTION    ""
   REFERENCE      "Win32_ProcessStartup.KeyIndex"
::= { win32ProcessStartupEntry 1 }

win32ProcessStartupCreateFlags OBJECT-TYPE
   SYNTAX         Uint32
   ACCESS         read-write
   STATUS         mandatory
   DESCRIPTION    ""
   REFERENCE      "Win32_ProcessStartup.CreateFlags"
::= { win32ProcessStartupEntry 2 }

win32ProcessStartupPriorityClass OBJECT-TYPE
   SYNTAX         Uint32
   ACCESS         read-write
   STATUS         mandatory
   DESCRIPTION    ""
   REFERENCE      "Win32_ProcessStartup.PriorityClass"
::= { win32ProcessStartupEntry 3 }

--win32ProcessStartupEnvironmentVariables OBJECT-TYPE
--   SYNTAX         String
--   ACCESS         read-write
--   STATUS         mandatory
--   DESCRIPTION    ""
--   REFERENCE      "Win32_ProcessStartup.EnvironmentVariables"
--::= { win32ProcessStartupEntry 4 }

win32ProcessStartupWinstationDesktop OBJECT-TYPE
   SYNTAX         String
   ACCESS         read-write
   STATUS         mandatory
   DESCRIPTION    ""
   REFERENCE      "Win32_ProcessStartup.Desktop"
::= { win32ProcessStartupEntry 5 }

win32ProcessStartupTitle OBJECT-TYPE
   SYNTAX         String
   ACCESS         read-write
   STATUS         mandatory
   DESCRIPTION    ""
   REFERENCE      "Win32_ProcessStartup.Title"
::= { win32ProcessStartupEntry 6 }

win32ProcessStartupX OBJECT-TYPE
   SYNTAX         Uint32
   ACCESS         read-write
   STATUS         mandatory
   DESCRIPTION    ""
   REFERENCE      "Win32_ProcessStartup.X"
::= { win32ProcessStartupEntry 7 }

win32ProcessStartupY OBJECT-TYPE
   SYNTAX         Uint32
   ACCESS         read-write
   STATUS         mandatory
   DESCRIPTION    ""
   REFERENCE      "Win32_ProcessStartup.Y"
::= { win32ProcessStartupEntry 8 }

win32ProcessStartupXSize OBJECT-TYPE
   SYNTAX         Uint32
   ACCESS         read-write
   STATUS         mandatory
   DESCRIPTION    ""
   REFERENCE      "Win32_ProcessStartup.XSize"
::= { win32ProcessStartupEntry 9 }

win32ProcessStartupYSize OBJECT-TYPE
   SYNTAX         Uint32
   ACCESS         read-write
   STATUS         mandatory
   DESCRIPTION    ""
   REFERENCE      "Win32_ProcessStartup.YSize"
::= { win32ProcessStartupEntry 10 }

win32ProcessStartupXCountChars OBJECT-TYPE
   SYNTAX         Uint32
   ACCESS         read-write
   STATUS         mandatory
   DESCRIPTION    ""
   REFERENCE      "Win32_ProcessStartup.XCountChars"
::= { win32ProcessStartupEntry 11 }

win32ProcessStartupYCountChars OBJECT-TYPE
   SYNTAX         Uint32
   ACCESS         read-write
   STATUS         mandatory
   DESCRIPTION    ""
   REFERENCE      "Win32_ProcessStartup.YCountChars"
::= { win32ProcessStartupEntry 12 }

win32ProcessStartupFillAttribute OBJECT-TYPE
   SYNTAX         Uint32
   ACCESS         read-write
   STATUS         mandatory
   DESCRIPTION    ""
   REFERENCE      "Win32_ProcessStartup.FillAttribute"
::= { win32ProcessStartupEntry 13 }

win32ProcessStartupShowWindow OBJECT-TYPE
   SYNTAX         Uint16
   ACCESS         read-write
   STATUS         mandatory
   DESCRIPTION    ""
   REFERENCE      "Win32_ProcessStartup.ShowError"
::= { win32ProcessStartupEntry 14 }

win32ProcessStartupErrorMode OBJECT-TYPE
   SYNTAX         Uint16
   ACCESS         read-write
   STATUS         mandatory
   DESCRIPTION    ""
   REFERENCE      "Win32_ProcessStartup.ErrorMode"
::= { win32ProcessStartupEntry 15 }

win32ProcessStartupStatus OBJECT-TYPE
   SYNTAX         String
   ACCESS         read-write
   STATUS         mandatory
   DESCRIPTION    "The Status property is a string indicating the current status of the object. Various operational and non-operational statuses can be defined. Operational statuses are OK, Degraded and Pred Fail. Pred Fail indicates that an element may be functioning properly but predicting a failure in the near future. An example is a SMART-enabled hard drive. Non-operational statuses can also be specified. These are Error, Starting, Stopping and Service. The latter, Service, could apply during mirror-resilvering of a disk, reload of a user permissions list, or other administrative work. Not all such work is on-line, yet the managed element is neither OK nor in one of the other states."
   REFERENCE      "Win32_ProcessStartup.Status"
::= { win32ProcessStartupEntry 16 }

win32ProcessTable OBJECT-TYPE
   SYNTAX         SEQUENCE OF Win32ProcessEntry
   ACCESS         not-accessible
   STATUS         mandatory
   DESCRIPTION    ""
   REFERENCE      "Win32_Process"
::= { win32WMI 410 }

win32ProcessEntry OBJECT-TYPE
   SYNTAX         Win32ProcessEntry
   ACCESS         not-accessible
   STATUS         mandatory
   DESCRIPTION    ""
   INDEX          { win32ProcessKeyIndex }
::= { win32ProcessTable 1 }

Win32ProcessEntry ::= SEQUENCE
{
   win32ProcessKeyIndex String,
   win32ProcessExecutablePath String,
   win32ProcessMaximumWorkingSetSize Uint32,
   win32ProcessMinimumWorkingSetSize Uint32,
   win32ProcessPageFaults Uint32,
   win32ProcessPageFileUsage Uint32,
   win32ProcessPeakWorkingSetSize Uint32,
   win32ProcessProcessId Uint32,
   win32ProcessQuotaNonPagedPoolUsage Uint32,
   win32ProcessQuotaPagedPoolUsage Uint32,
   win32ProcessQuotaPeakNonPagedPoolUsage Uint32,
   win32ProcessQuotaPeakPagedPoolUsage Uint32,
   win32ProcessWindowsVersion String,
   win32ProcessStatus String
}

win32ProcessKeyIndex OBJECT-TYPE
   SYNTAX         String
   ACCESS         read-write
   STATUS         mandatory
   DESCRIPTION    ""
   REFERENCE      "Win32_Process.KeyIndex"
::= { win32ProcessEntry 1 }

win32ProcessExecutablePath OBJECT-TYPE
   SYNTAX         String
   ACCESS         read-write
   STATUS         mandatory
   DESCRIPTION    ""
   REFERENCE      "Win32_Process.ExecutablePath"
::= { win32ProcessEntry 2 }

win32ProcessMaximumWorkingSetSize OBJECT-TYPE
   SYNTAX         Uint32
   ACCESS         read-write
   STATUS         mandatory
   DESCRIPTION    ""
   REFERENCE      "Win32_Process.MaximumWorkingSetSize"
::= { win32ProcessEntry 3 }

win32ProcessMinimumWorkingSetSize OBJECT-TYPE
   SYNTAX         Uint32
   ACCESS         read-write
   STATUS         mandatory
   DESCRIPTION    ""
   REFERENCE      "Win32_Process.MinimumWorkingSetSize"
::= { win32ProcessEntry 4 }

win32ProcessPageFaults OBJECT-TYPE
   SYNTAX         Uint32
   ACCESS         read-write
   STATUS         mandatory
   DESCRIPTION    ""
   REFERENCE      "Win32_Process.PageFaults"
::= { win32ProcessEntry 5 }

win32ProcessPageFileUsage OBJECT-TYPE
   SYNTAX         Uint32
   ACCESS         read-write
   STATUS         mandatory
   DESCRIPTION    ""
   REFERENCE      "Win32_Process.PageFileUsage"
::= { win32ProcessEntry 6 }

win32ProcessPeakWorkingSetSize OBJECT-TYPE
   SYNTAX         Uint32
   ACCESS         read-write
   STATUS         mandatory
   DESCRIPTION    ""
   REFERENCE      "Win32_Process.PeakWorkingSetSize"
::= { win32ProcessEntry 7 }

win32ProcessProcessId OBJECT-TYPE
   SYNTAX         Uint32
   ACCESS         read-write
   STATUS         mandatory
   DESCRIPTION    ""
   REFERENCE      "Win32_Process.ProcessId"
::= { win32ProcessEntry 8 }

win32ProcessQuotaNonPagedPoolUsage OBJECT-TYPE
   SYNTAX         Uint32
   ACCESS         read-write
   STATUS         mandatory
   DESCRIPTION    ""
   REFERENCE      "Win32_Process.QuotaNonPagedPoolUsage"
::= { win32ProcessEntry 9 }

win32ProcessQuotaPagedPoolUsage OBJECT-TYPE
   SYNTAX         Uint32
   ACCESS         read-write
   STATUS         mandatory
   DESCRIPTION    ""
   REFERENCE      "Win32_Process.QuotaPagePoolUsage"
::= { win32ProcessEntry 10 }

win32ProcessQuotaPeakNonPagedPoolUsage OBJECT-TYPE
   SYNTAX         Uint32
   ACCESS         read-write
   STATUS         mandatory
   DESCRIPTION    ""
   REFERENCE      "Win32_Process.QuotaPeakNonPagedPoolUsage"
::= { win32ProcessEntry 11 }

win32ProcessQuotaPeakPagedPoolUsage OBJECT-TYPE
   SYNTAX         Uint32
   ACCESS         read-write
   STATUS         mandatory
   DESCRIPTION    ""
   REFERENCE      "Win32_Process.QuotaPeakPagedPoolUsage"
::= { win32ProcessEntry 12 }

win32ProcessWindowsVersion OBJECT-TYPE
   SYNTAX         String
   ACCESS         read-write
   STATUS         mandatory
   DESCRIPTION    ""
   REFERENCE      "Win32_Process.WindowsVersion"
::= { win32ProcessEntry 13 }

win32ProcessStatus OBJECT-TYPE
   SYNTAX         String
   ACCESS         read-write
   STATUS         mandatory
   DESCRIPTION    "The Status property is a string indicating the current status of the object. Various operational and non-operational statuses can be defined. Operational statuses are OK, Degraded and Pred Fail. Pred Fail indicates that an element may be functioning properly but predicting a failure in the near future. An example is a SMART-enabled hard drive. Non-operational statuses can also be specified. These are Error, Starting, Stopping and Service. The latter, Service, could apply during mirror-resilvering of a disk, reload of a user permissions list, or other administrative work. Not all such work is on-line, yet the managed element is neither OK nor in one of the other states."
   REFERENCE      "Win32_Process.Status"
::= { win32ProcessEntry 14 }

win32ThreadTable OBJECT-TYPE
   SYNTAX         SEQUENCE OF Win32ThreadEntry
   ACCESS         not-accessible
   STATUS         mandatory
   DESCRIPTION    ""
   REFERENCE      "Win32_Thread"
::= { win32WMI 420 }

win32ThreadEntry OBJECT-TYPE
   SYNTAX         Win32ThreadEntry
   ACCESS         not-accessible
   STATUS         mandatory
   DESCRIPTION    ""
   INDEX          { win32ThreadKeyIndex }
::= { win32ThreadTable 1 }

Win32ThreadEntry ::= SEQUENCE
{
   win32ThreadKeyIndex String,
   win32ThreadProcessHandle String,
   win32ThreadHandle String,
   win32ThreadElapsedTime String,
   win32ThreadPriorityBase Uint32,
   win32ThreadPriority Uint32,
   win32ThreadStartAddress Uint32,
   win32ThreadThreadState Uint32,
   win32ThreadThreadWaitReason Uint32,
   win32ThreadStatus String
}

win32ThreadKeyIndex OBJECT-TYPE
   SYNTAX         String
   ACCESS         read-write
   STATUS         mandatory
   DESCRIPTION    ""
   REFERENCE      "Win32_Thread.KeyIndex"
::= { win32ThreadEntry 1 }

win32ThreadProcessHandle OBJECT-TYPE
   SYNTAX         String
   ACCESS         read-write
   STATUS         mandatory
   DESCRIPTION    ""
   REFERENCE      "Win32_Thread.ProcessHandle"
::= { win32ThreadEntry 2 }

win32ThreadHandle OBJECT-TYPE
   SYNTAX         String
   ACCESS         read-write
   STATUS         mandatory
   DESCRIPTION    ""
   REFERENCE      "Win32_Thread.Handle"
::= { win32ThreadEntry 3 }

win32ThreadElapsedTime OBJECT-TYPE
   SYNTAX         String
   ACCESS         read-write
   STATUS         mandatory
   DESCRIPTION    ""
   REFERENCE      "Win32_Thread.ElapsedTime"
::= { win32ThreadEntry 4 }

win32ThreadPriorityBase OBJECT-TYPE
   SYNTAX         Uint32
   ACCESS         read-write
   STATUS         mandatory
   DESCRIPTION    ""
   REFERENCE      "Win32_Thread.PriorityBase"
::= { win32ThreadEntry 5 }

win32ThreadPriority OBJECT-TYPE
   SYNTAX         Uint32
   ACCESS         read-write
   STATUS         mandatory
   DESCRIPTION    ""
   REFERENCE      "Win32_Thread.ThreadPriority"
::= { win32ThreadEntry 6 }

win32ThreadStartAddress OBJECT-TYPE
   SYNTAX         Uint32
   ACCESS         read-write
   STATUS         mandatory
   DESCRIPTION    ""
   REFERENCE      "Win32_Thread.StartAddress"
::= { win32ThreadEntry 7 }

win32ThreadThreadState OBJECT-TYPE
   SYNTAX         Uint32
   ACCESS         read-write
   STATUS         mandatory
   DESCRIPTION    ""
   REFERENCE      "Win32_Thread.ThreadState"
::= { win32ThreadEntry 8 }

win32ThreadThreadWaitReason OBJECT-TYPE
   SYNTAX         Uint32
   ACCESS         read-write
   STATUS         mandatory
   DESCRIPTION    ""
   REFERENCE      "Win32_Thread.ThreadWaitReason"
::= { win32ThreadEntry 9 }

win32ThreadStatus OBJECT-TYPE
   SYNTAX         String
   ACCESS         read-write
   STATUS         mandatory
   DESCRIPTION    "The Status property is a string indicating the current status of the object. Various operational and non-operational statuses can be defined. Operational statuses are OK, Degraded and Pred Fail. Pred Fail indicates that an element may be functioning properly but predicting a failure in the near future. An example is a SMART-enabled hard drive. Non-operational statuses can also be specified. These are Error, Starting, Stopping and Service. The latter, Service, could apply during mirror-resilvering of a disk, reload of a user permissions list, or other administrative work. Not all such work is on-line, yet the managed element is neither OK nor in one of the other states."
   REFERENCE      "Win32_Thread.Status"
::= { win32ThreadEntry 10 }

win32OperatingSystemTable OBJECT-TYPE
   SYNTAX         SEQUENCE OF Win32OperatingSystemEntry
   ACCESS         not-accessible
   STATUS         mandatory
   DESCRIPTION    "The Win32_OperatingSystem class represents an operating system installed on a Win32 system. Any operating system that can be installed on a Win32 system is a descendent (or member) of this class.<P>Example: Microsoft Windows 95"
   REFERENCE      "Win32_OperatingSystem"
::= { win32WMI 430 }

win32OperatingSystemEntry OBJECT-TYPE
   SYNTAX         Win32OperatingSystemEntry
   ACCESS         not-accessible
   STATUS         mandatory
   DESCRIPTION    ""
   INDEX          { win32OperatingSystemKeyIndex }
::= { win32OperatingSystemTable 1 }

Win32OperatingSystemEntry ::= SEQUENCE
{
   win32OperatingSystemKeyIndex String,
   win32OperatingSystemBootDevice String,
   win32OperatingSystemBuildNumber String,
   win32OperatingSystemBuildType String,
   win32OperatingSystemCodeSet String,
   win32OperatingSystemCountryCode String,
   win32OperatingSystemCSDVersion String,
   win32OperatingSystemDebug Boolean,
   win32OperatingSystemForegroundApplicationBoost Uint8,
   win32OperatingSystemLocale String,
   win32OperatingSystemManufacturer String,
   win32OperatingSystemOrganization String,
   win32OperatingSystemOSLanguage Uint32,
   win32OperatingSystemPlusProductID String,
   win32OperatingSystemPlusVersionNumber String,
   win32OperatingSystemPrimary Boolean,
   win32OperatingSystemQuantumLength Uint8,
   win32OperatingSystemQuantumType Uint8,
   win32OperatingSystemRegisteredUser String,
   win32OperatingSystemSerialNumber String,
   win32OperatingSystemSystemDevice String,
   win32OperatingSystemSystemDirectory String,
   win32OperatingSystemVersion String,
   win32OperatingSystemWindowsDirectory String,
   win32OperatingSystemDescription String,
   win32OperatingSystemStatus String
}

win32OperatingSystemKeyIndex OBJECT-TYPE
   SYNTAX         String
   ACCESS         read-write
   STATUS         mandatory
   DESCRIPTION    ""
   REFERENCE      "Win32_OperatingSystem.KeyIndex"
::= { win32OperatingSystemEntry 1 }

win32OperatingSystemBootDevice OBJECT-TYPE
   SYNTAX         String
   ACCESS         read-write
   STATUS         mandatory
   DESCRIPTION    "The BootDevice property indicates the name of the boot device for the Win32 operating system.<P> Example: \\Device\\Harddisk0\\partition1"
   REFERENCE      "Win32_OperatingSystem.BootDevice"
::= { win32OperatingSystemEntry 2 }

win32OperatingSystemBuildNumber OBJECT-TYPE
   SYNTAX         String
   ACCESS         read-write
   STATUS         mandatory
   DESCRIPTION    "The BuildNumber property indicates the build number of the operating system.<P>Example: 1381"
   REFERENCE      "Win32_OperatingSystem.BuildNumber"
::= { win32OperatingSystemEntry 3 }

win32OperatingSystemBuildType OBJECT-TYPE
   SYNTAX         String
   ACCESS         read-write
   STATUS         mandatory
   DESCRIPTION    "The BuildType property indicates the type of build used for the operating system."
   REFERENCE      "Win32_OperatingSystem.BuildType"
::= { win32OperatingSystemEntry 4 }

win32OperatingSystemCodeSet OBJECT-TYPE
   SYNTAX         String
   ACCESS         read-write
   STATUS         mandatory
   DESCRIPTION    "The CodeSet property indicates the code that is set for the operating system."
   REFERENCE      "Win32_OperatingSystem.CodeSet"
::= { win32OperatingSystemEntry 5 }

win32OperatingSystemCountryCode OBJECT-TYPE
   SYNTAX         String
   ACCESS         read-write
   STATUS         mandatory
   DESCRIPTION    "The CountryCode property indicates the locale of the operating system.<P>Example: 00000409"
   REFERENCE      "Win32_OperatingSystem.CountryCode"
::= { win32OperatingSystemEntry 6 }

win32OperatingSystemCSDVersion OBJECT-TYPE
   SYNTAX         String
   ACCESS         read-write
   STATUS         mandatory
   DESCRIPTION    "The CSDVersion property indicates the CSD version of the operating system.<P>Example: B"
   REFERENCE      "Win32_OperatingSystem.CSDVersion"
::= { win32OperatingSystemEntry 7 }

win32OperatingSystemDebug OBJECT-TYPE
   SYNTAX         Boolean
   ACCESS         read-write
   STATUS         mandatory
   DESCRIPTION    ""
   REFERENCE      "Win32_OperatingSystem.Debug"
::= { win32OperatingSystemEntry 8 }

win32OperatingSystemForegroundApplicationBoost OBJECT-TYPE
   SYNTAX         Uint8
   ACCESS         read-write
   STATUS         mandatory
   DESCRIPTION    "The ForegroundApplicationBoost property indicates the amount of priority CPU time allocated to the foreground application."
   REFERENCE      "Win32_OperatingSystem.ForegroundApplicationBoost"
::= { win32OperatingSystemEntry 9 }

win32OperatingSystemLocale OBJECT-TYPE
   SYNTAX         String
   ACCESS         read-write
   STATUS         mandatory
   DESCRIPTION    "The Locale property indicates the system default locale of the operating system."
   REFERENCE      "Win32_OperatingSystem.Locale"
::= { win32OperatingSystemEntry 10 }

win32OperatingSystemManufacturer OBJECT-TYPE
   SYNTAX         String
   ACCESS         read-write
   STATUS         mandatory
   DESCRIPTION    "The Manufacturer property indicates the name of the operating system manaufacturer.<P>Example: Microsoft"
   REFERENCE      "Win32_OperatingSystem.Manufacturer"
::= { win32OperatingSystemEntry 11 }

win32OperatingSystemOrganization OBJECT-TYPE
   SYNTAX         String
   ACCESS         read-write
   STATUS         mandatory
   DESCRIPTION    "The Organization property indicates the company name of the registered user of the operating system.<P>Example: Jane Doe"
   REFERENCE      "Win32_OperatingSystem.Organization"
::= { win32OperatingSystemEntry 12 }

win32OperatingSystemOSLanguage OBJECT-TYPE
   SYNTAX         Uint32
   ACCESS         read-write
   STATUS         mandatory
   DESCRIPTION    "The OSLanguage property indicates which language version of the os is installed.<P>Example: If a German version of NT is installed, this value would be 1031 (or 0x407)"
   REFERENCE      "Win32_OperatingSystem.OSLanguage"
::= { win32OperatingSystemEntry 13 }

win32OperatingSystemPlusProductID OBJECT-TYPE
   SYNTAX         String
   ACCESS         read-write
   STATUS         mandatory
   DESCRIPTION    ""
   REFERENCE      "Win32_OperatingSystem.PlusProductID"
::= { win32OperatingSystemEntry 14 }

win32OperatingSystemPlusVersionNumber OBJECT-TYPE
   SYNTAX         String
   ACCESS         read-write
   STATUS         mandatory
   DESCRIPTION    ""
   REFERENCE      "Win32_OperatingSystem.PlusVersionNumber"
::= { win32OperatingSystemEntry 15 }

win32OperatingSystemPrimary OBJECT-TYPE
   SYNTAX         Boolean
   ACCESS         read-write
   STATUS         mandatory
   DESCRIPTION    "The Primary property determines whether this is the primary operating system.<P>Values: TRUE or FALSE. If TRUE, this is the primary operating system."
   REFERENCE      "Win32_OperatingSystem.Primary"
::= { win32OperatingSystemEntry 16 }

win32OperatingSystemQuantumLength OBJECT-TYPE
   SYNTAX         Uint8
   ACCESS         read-write
   STATUS         mandatory
   DESCRIPTION    ""
   REFERENCE      "Win32_OperatingSystem.QuantumLength"
::= { win32OperatingSystemEntry 17 }

win32OperatingSystemQuantumType OBJECT-TYPE
   SYNTAX         Uint8
   ACCESS         read-write
   STATUS         mandatory
   DESCRIPTION    ""
   REFERENCE      "Win32_OperatingSystem.QuantumType"
::= { win32OperatingSystemEntry 18 }

win32OperatingSystemRegisteredUser OBJECT-TYPE
   SYNTAX         String
   ACCESS         read-write
   STATUS         mandatory
   DESCRIPTION    "The RegisteredUser property indicates the name of the registered user of the operating system.<P>Example: Jane Doe"
   REFERENCE      "Win32_OperatingSystem.RegisteredUser"
::= { win32OperatingSystemEntry 19 }

win32OperatingSystemSerialNumber OBJECT-TYPE
   SYNTAX         String
   ACCESS         read-write
   STATUS         mandatory
   DESCRIPTION    "The SerialNumber property indicates the Windows directory of the operating system.<P>Example:10497-OEM-0031416-71674"
   REFERENCE      "Win32_OperatingSystem.SerialNumber"
::= { win32OperatingSystemEntry 20 }

win32OperatingSystemSystemDevice OBJECT-TYPE
   SYNTAX         String
   ACCESS         read-write
   STATUS         mandatory
   DESCRIPTION    ""
   REFERENCE      "Win32_OperatingSystem.SystemDevice"
::= { win32OperatingSystemEntry 21 }

win32OperatingSystemSystemDirectory OBJECT-TYPE
   SYNTAX         String
   ACCESS         read-write
   STATUS         mandatory
   DESCRIPTION    "The SystemDirectory property indicates the system directory of the operating system.<P>Example: C:\\WINDOWS\\SYSTEM32"
   REFERENCE      "Win32_OperatingSystem.SystemDirectory"
::= { win32OperatingSystemEntry 22 }

win32OperatingSystemVersion OBJECT-TYPE
   SYNTAX         String
   ACCESS         read-write
   STATUS         mandatory
   DESCRIPTION    "The Version property indicates the version number of the operating system manaufacturer.<P>Example: 4.0"
   REFERENCE      "Win32_OperatingSystem.Version"
::= { win32OperatingSystemEntry 23 }

win32OperatingSystemWindowsDirectory OBJECT-TYPE
   SYNTAX         String
   ACCESS         read-write
   STATUS         mandatory
   DESCRIPTION    "The WindowsDirectory property indicates the Windows directory of the operating system.<P>Example: C:\\WINDOWS"
   REFERENCE      "Win32_OperatingSystem.WindowsDirectory"
::= { win32OperatingSystemEntry 24 }

win32OperatingSystemDescription OBJECT-TYPE
   SYNTAX         String
   ACCESS         read-write
   STATUS         mandatory
   DESCRIPTION    "The Description property provides a textual description of the Win32 operating system.   Some user interfaces that allow editing of this description limit its length to 48 characters."
   REFERENCE      "Win32_OperatingSystem.Description"
::= { win32OperatingSystemEntry 25 }

win32OperatingSystemStatus OBJECT-TYPE
   SYNTAX         String
   ACCESS         read-write
   STATUS         mandatory
   DESCRIPTION    "The Status property is a string indicating the current status of the object. Various operational and non-operational statuses can be defined. Operational statuses are OK, Degraded and Pred Fail. Pred Fail indicates that an element may be functioning properly but predicting a failure in the near future. An example is a SMART-enabled hard drive. Non-operational statuses can also be specified. These are Error, Starting, Stopping and Service. The latter, Service, could apply during mirror-resilvering of a disk, reload of a user permissions list, or other administrative work. Not all such work is on-line, yet the managed element is neither OK nor in one of the other states."
   REFERENCE      "Win32_OperatingSystem.Status"
::= { win32OperatingSystemEntry 26 }

win32PrintJobTable OBJECT-TYPE
   SYNTAX         SEQUENCE OF Win32PrintJobEntry
   ACCESS         not-accessible
   STATUS         mandatory
   DESCRIPTION    "The Win32_PrintJob class represents a print job generated by a Win32 application. Any unit of work generated by the Print command of an application running on a Win32 system is a descendent (or member) of this class.<P>Example: A print document created by an Office 97 application"
   REFERENCE      "Win32_PrintJob"
::= { win32WMI 440 }

win32PrintJobEntry OBJECT-TYPE
   SYNTAX         Win32PrintJobEntry
   ACCESS         not-accessible
   STATUS         mandatory
   DESCRIPTION    ""
   INDEX          { win32PrintJobKeyIndex }
::= { win32PrintJobTable 1 }

Win32PrintJobEntry ::= SEQUENCE
{
   win32PrintJobKeyIndex String,
   win32PrintJobName String,
   win32PrintJobDataType String,
   win32PrintJobDocument String,
   win32PrintJobDriverName String,
   win32PrintJobHostPrintQueue String,
   win32PrintJobJobId Uint32,
   win32PrintJobPagesPrinted Uint32,
   win32PrintJobParameters String,
   win32PrintJobPrintProcessor String,
   win32PrintJobSize Uint32,
   win32PrintJobTotalPages Uint32,
   win32PrintJobStatus String
}

win32PrintJobKeyIndex OBJECT-TYPE
   SYNTAX         String
   ACCESS         read-write
   STATUS         mandatory
   DESCRIPTION    ""
   REFERENCE      "Win32_PrintJob.KeyIndex"
::= { win32PrintJobEntry 1 }

win32PrintJobName OBJECT-TYPE
   SYNTAX         String
   ACCESS         read-write
   STATUS         mandatory
   DESCRIPTION    "The inherited Name serves as key of a Job instance in the context of an PrintJob."
   REFERENCE      "Win32_PrintJob.Name"
::= { win32PrintJobEntry 2 }

win32PrintJobDataType OBJECT-TYPE
   SYNTAX         String
   ACCESS         read-write
   STATUS         mandatory
   DESCRIPTION    "The DataType property indicates the data type of the print job."
   REFERENCE      "Win32_PrintJob.DataType"
::= { win32PrintJobEntry 3 }

win32PrintJobDocument OBJECT-TYPE
   SYNTAX         String
   ACCESS         read-write
   STATUS         mandatory
   DESCRIPTION    "The Document property indicates the name of the document to be printed."
   REFERENCE      "Win32_PrintJob.Document"
::= { win32PrintJobEntry 4 }

win32PrintJobDriverName OBJECT-TYPE
   SYNTAX         String
   ACCESS         read-write
   STATUS         mandatory
   DESCRIPTION    "The DriverName property indicates the name of the printer drive used for the print job."
   REFERENCE      "Win32_PrintJob.DriverName"
::= { win32PrintJobEntry 5 }

win32PrintJobHostPrintQueue OBJECT-TYPE
   SYNTAX         String
   ACCESS         read-write
   STATUS         mandatory
   DESCRIPTION    "The HostPrintQueue property indicates the name of the host print queue."
   REFERENCE      "Win32_PrintJob.HostPrintQueue"
::= { win32PrintJobEntry 6 }

win32PrintJobJobId OBJECT-TYPE
   SYNTAX         Uint32
   ACCESS         read-write
   STATUS         mandatory
   DESCRIPTION    "The JobId property indicates the identifier number of the job."
   REFERENCE      "Win32_PrintJob.JobId"
::= { win32PrintJobEntry 7 }

win32PrintJobPagesPrinted OBJECT-TYPE
   SYNTAX         Uint32
   ACCESS         read-write
   STATUS         mandatory
   DESCRIPTION    "The PagesPrinted property indicates the number pages printed."
   REFERENCE      "Win32_PrintJob.PagesPrinted"
::= { win32PrintJobEntry 8 }

win32PrintJobParameters OBJECT-TYPE
   SYNTAX         String
   ACCESS         read-write
   STATUS         mandatory
   DESCRIPTION    "The Parameters property indicates the printing parameters of the print job."
   REFERENCE      "Win32_PrintJob.Parameters"
::= { win32PrintJobEntry 9 }

win32PrintJobPrintProcessor OBJECT-TYPE
   SYNTAX         String
   ACCESS         read-write
   STATUS         mandatory
   DESCRIPTION    "The PrintProcessor property indicates the service used to process the print job."
   REFERENCE      "Win32_PrintJob.PrintProcessor"
::= { win32PrintJobEntry 10 }

win32PrintJobSize OBJECT-TYPE
   SYNTAX         Uint32
   ACCESS         read-write
   STATUS         mandatory
   DESCRIPTION    "The Size property indicates the size (in bytes) of the print job."
   REFERENCE      "Win32_PrintJob.Size"
::= { win32PrintJobEntry 11 }

win32PrintJobTotalPages OBJECT-TYPE
   SYNTAX         Uint32
   ACCESS         read-write
   STATUS         mandatory
   DESCRIPTION    "The TotalPages property indicates the total page count submitted as the print job."
   REFERENCE      "Win32_PrintJob.TotalPages"
::= { win32PrintJobEntry 12 }

win32PrintJobStatus OBJECT-TYPE
   SYNTAX         String
   ACCESS         read-write
   STATUS         mandatory
   DESCRIPTION    "The Status property is a string indicating the current status of the object. Various operational and non-operational statuses can be defined. Operational statuses are OK, Degraded and Pred Fail. Pred Fail indicates that an element may be functioning properly but predicting a failure in the near future. An example is a SMART-enabled hard drive. Non-operational statuses can also be specified. These are Error, Starting, Stopping and Service. The latter, Service, could apply during mirror-resilvering of a disk, reload of a user permissions list, or other administrative work. Not all such work is on-line, yet the managed element is neither OK nor in one of the other states."
   REFERENCE      "Win32_PrintJob.Status"
::= { win32PrintJobEntry 13 }

win32ScheduledJobTable OBJECT-TYPE
   SYNTAX         SEQUENCE OF Win32ScheduledJobEntry
   ACCESS         not-accessible
   STATUS         mandatory
   DESCRIPTION    "The Win32_ScheduledJob class represents a job scheduled using the NT schedule service. This class isonly instrumented on NT3.51 and upwards. Each job scheduled against the NT schedule service is stored persistently and is executed at the specified time and day of the week and/or month. If the machine is not active or if thescheduled service is not running at the specified job time the schedule service will run the specified job on thenext day at the specified time.Scheduled jobs are scheduled with respect to UTC time, i.e. with bias offset from GMT. This means that a job can bespecified using any time zone specification. The Win32_ScheduledJob class will return the local time with UTC offsetwhen enumerating object and convert to local time when creating new jobs. For example a job specified to run on a computer in Chicago at 10:30 pm Monday PST time will be scheduled to run locally at 12:30am Tuesday CET. It should be noted that a client must take into account whether daylight..."
   REFERENCE      "Win32_ScheduledJob"
::= { win32WMI 450 }

win32ScheduledJobEntry OBJECT-TYPE
   SYNTAX         Win32ScheduledJobEntry
   ACCESS         not-accessible
   STATUS         mandatory
   DESCRIPTION    ""
   INDEX          { win32ScheduledJobKeyIndex }
::= { win32ScheduledJobTable 1 }

Win32ScheduledJobEntry ::= SEQUENCE
{
   win32ScheduledJobKeyIndex String,
   win32ScheduledJobJobId Uint32,
   win32ScheduledJobCommand String,
   win32ScheduledJobStartTime Datetime,
   win32ScheduledJobRunRepeatedly Boolean,
   win32ScheduledJobInteractWithDesktop Boolean,
   win32ScheduledJobDaysOfWeek Uint32,
   win32ScheduledJobDaysOfMonth Uint32,
   win32ScheduledJobJobStatus String,
   win32ScheduledJobStatus String
}

win32ScheduledJobKeyIndex OBJECT-TYPE
   SYNTAX         String
   ACCESS         read-write
   STATUS         mandatory
   DESCRIPTION    ""
   REFERENCE      "Win32_ScheduledJob.KeyIndex"
::= { win32ScheduledJobEntry 1 }

win32ScheduledJobJobId OBJECT-TYPE
   SYNTAX         Uint32
   ACCESS         read-write
   STATUS         mandatory
   DESCRIPTION    "Unique identifier for the job."
   REFERENCE      "Win32_ScheduledJob.JobId"
::= { win32ScheduledJobEntry 2 }

win32ScheduledJobCommand OBJECT-TYPE
   SYNTAX         String
   ACCESS         read-write
   STATUS         mandatory
   DESCRIPTION    "Command represents the executable name and command line arguments that the schedule service will use to invoke the job.Example. 'defrag /q /f'"
   REFERENCE      "Win32_ScheduledJob.Command"
::= { win32ScheduledJobEntry 3 }

win32ScheduledJobStartTime OBJECT-TYPE
   SYNTAX         Datetime
   ACCESS         read-write
   STATUS         mandatory
   DESCRIPTION    "StartTime represents the UTC time to run the job. This is of the form YYYYMMDDHHMMSS.MMMMMM(+-)OOO, where YYYYMMDD must be replaced by ****** Example. ********123000.000000-420 which implies 12:30 pm PST with daylight savings time in effect"
   REFERENCE      "Win32_ScheduledJob.StartTime"
::= { win32ScheduledJobEntry 4 }

win32ScheduledJobRunRepeatedly OBJECT-TYPE
   SYNTAX         Boolean
   ACCESS         read-write
   STATUS         mandatory
   DESCRIPTION    "RunRepeatedly represents whether the scheduled job, once created, will continue to run repeatedlyafter the first invocation of the job. Specify TRUE to repeatedly run the job, FALSE to run the job once anda value null to indicate to run the job once"
   REFERENCE      "Win32_ScheduledJob.RunRepeatedly"
::= { win32ScheduledJobEntry 5 }

win32ScheduledJobInteractWithDesktop OBJECT-TYPE
   SYNTAX         Boolean
   ACCESS         read-write
   STATUS         mandatory
   DESCRIPTION    "Allow the specified Job to interacted with desktop. A value or TRUE or null indicates that the job willbe allowed to interact with the interactive desktop, a value of FALSE indicates that the job will runin a separate desktop"
   REFERENCE      "Win32_ScheduledJob.InteractWithDesktop"
::= { win32ScheduledJobEntry 6 }

win32ScheduledJobDaysOfWeek OBJECT-TYPE
   SYNTAX         Uint32
   ACCESS         read-write
   STATUS         mandatory
   DESCRIPTION    "DaysOfWeek represents what days of the week the job will be run on. If a Job has value null for both DaysOfWeek and DaysOfMonth,then the Job will be run either today or tomorrow depending on the specified StartTime and the current local time i.e. if it is12:30am and the job was created at 12:31am then the job will be run the following day.The value is a bitmask representing the day of the week, Sunday is specified as bit 0 and Saturday as bit 6. Each day can beinclusively Or'd to form a 7 bit value indicating the days of the week to run the job."
   REFERENCE      "Win32_ScheduledJob.DaysOfWeek"
::= { win32ScheduledJobEntry 7 }

win32ScheduledJobDaysOfMonth OBJECT-TYPE
   SYNTAX         Uint32
   ACCESS         read-write
   STATUS         mandatory
   DESCRIPTION    "DaysOfMonth represents what days of the month the job will be run on. If a Job has value null for both DaysOfWeek and DaysOfMonth,then the Job will be run either today or tomorrow depending on the specified StartTime and the current local time i.e. if it is12:30am and the job was created at 12:31am then the job will be run the following day.The value is a bitmask representing the day of the month, the first day of the month is specified as bit 0 and and the last day of the month is specified as bit 30. Each month can beinclusively Or'd to form a 31 bit value indicating the days of the week to run the job.If the current month does not contain all 31 days within a month, the job will not be run for that particular day of the month"
   REFERENCE      "Win32_ScheduledJob.DaysOfMonth"
::= { win32ScheduledJobEntry 8 }

win32ScheduledJobJobStatus OBJECT-TYPE
   SYNTAX         String
   ACCESS         read-write
   STATUS         mandatory
   DESCRIPTION    "JobStatus represents whether a Job created to run Repeatedly has been invocated at least once and that the last attempt resultedin a failure condition. Note that the JobStatus value 'Success' does not indicate that the job has already been run."
   REFERENCE      "Win32_ScheduledJob.JobStatus"
::= { win32ScheduledJobEntry 9 }

win32ScheduledJobStatus OBJECT-TYPE
   SYNTAX         String
   ACCESS         read-write
   STATUS         mandatory
   DESCRIPTION    "The Status property is a string indicating the current status of the object. Various operational and non-operational statuses can be defined. Operational statuses are OK, Degraded and Pred Fail. Pred Fail indicates that an element may be functioning properly but predicting a failure in the near future. An example is a SMART-enabled hard drive. Non-operational statuses can also be specified. These are Error, Starting, Stopping and Service. The latter, Service, could apply during mirror-resilvering of a disk, reload of a user permissions list, or other administrative work. Not all such work is on-line, yet the managed element is neither OK nor in one of the other states."
   REFERENCE      "Win32_ScheduledJob.Status"
::= { win32ScheduledJobEntry 10 }

win32BIOSTable OBJECT-TYPE
   SYNTAX         SEQUENCE OF Win32BIOSEntry
   ACCESS         not-accessible
   STATUS         mandatory
   DESCRIPTION    "The Win32_BIOS class represents the attributes for only the System BIOS installed on a Win32 system.<P>Example: Phoenix ROM BIOS PLUS Version 1.10 A14"
   REFERENCE      "Win32_BIOS"
::= { win32WMI 460 }

win32BIOSEntry OBJECT-TYPE
   SYNTAX         Win32BIOSEntry
   ACCESS         not-accessible
   STATUS         mandatory
   DESCRIPTION    ""
   INDEX          { win32BIOSKeyIndex }
::= { win32BIOSTable 1 }

Win32BIOSEntry ::= SEQUENCE
{
   win32BIOSKeyIndex String,
   win32BIOSReleaseDate Datetime,
   win32BIOSVersion String,
   win32BIOSStatus String
}

win32BIOSKeyIndex OBJECT-TYPE
   SYNTAX         String
   ACCESS         read-write
   STATUS         mandatory
   DESCRIPTION    ""
   REFERENCE      "Win32_BIOS.KeyIndex"
::= { win32BIOSEntry 1 }

win32BIOSReleaseDate OBJECT-TYPE
   SYNTAX         Datetime
   ACCESS         read-write
   STATUS         mandatory
   DESCRIPTION    "The ReleaseDate property indicates the release date of the Win32 BIOS.<P>Example: 19521201000230.000000000 (that is, 2 minutes 30 seconds after midnight 1st December 1952)"
   REFERENCE      "Win32_BIOS.ReleaseDate"
::= { win32BIOSEntry 2 }

win32BIOSVersion OBJECT-TYPE
   SYNTAX         String
   ACCESS         read-write
   STATUS         mandatory
   DESCRIPTION    "The Version property indicates the version of the Bios.<P>Example: 'BIOS Version 1.00.01.CN0T'"
   REFERENCE      "Win32_BIOS.Version"
::= { win32BIOSEntry 3 }

win32BIOSStatus OBJECT-TYPE
   SYNTAX         String
   ACCESS         read-write
   STATUS         mandatory
   DESCRIPTION    "The Status property is a string indicating the current status of the object. Various operational and non-operational statuses can be defined. Operational statuses are OK, Degraded and Pred Fail. Pred Fail indicates that an element may be functioning properly but predicting a failure in the near future. An example is a SMART-enabled hard drive. Non-operational statuses can also be specified. These are Error, Starting, Stopping and Service. The latter, Service, could apply during mirror-resilvering of a disk, reload of a user permissions list, or other administrative work. Not all such work is on-line, yet the managed element is neither OK nor in one of the other states."
   REFERENCE      "Win32_BIOS.Status"
::= { win32BIOSEntry 4 }

win32BootConfigurationTable OBJECT-TYPE
   SYNTAX         SEQUENCE OF Win32BootConfigurationEntry
   ACCESS         not-accessible
   STATUS         mandatory
   DESCRIPTION    "The Win32_BootConfiguration class represents the boot configuration on a Win32 system."
   REFERENCE      "Win32_BootConfiguration"
::= { win32WMI 470 }

win32BootConfigurationEntry OBJECT-TYPE
   SYNTAX         Win32BootConfigurationEntry
   ACCESS         not-accessible
   STATUS         mandatory
   DESCRIPTION    ""
   INDEX          { win32BootConfigurationKeyIndex }
::= { win32BootConfigurationTable 1 }

Win32BootConfigurationEntry ::= SEQUENCE
{
   win32BootConfigurationKeyIndex String,
   win32BootConfigurationBootDirectory String,
   win32BootConfigurationConfigurationPath String,
   win32BootConfigurationLastDrive String,
   win32BootConfigurationName String,
   win32BootConfigurationScratchDirectory String,
   win32BootConfigurationTempDirectory String
}

win32BootConfigurationKeyIndex OBJECT-TYPE
   SYNTAX         String
   ACCESS         read-write
   STATUS         mandatory
   DESCRIPTION    ""
   REFERENCE      "Win32_BootConfiguration.KeyIndex"
::= { win32BootConfigurationEntry 1 }

win32BootConfigurationBootDirectory OBJECT-TYPE
   SYNTAX         String
   ACCESS         read-write
   STATUS         mandatory
   DESCRIPTION    "The BootDirectory property indicates the directory location of the system files required for booting the system.<P>Example: Typically, this is the root directory."
   REFERENCE      "Win32_BootConfiguration.BootDirectory"
::= { win32BootConfigurationEntry 2 }

win32BootConfigurationConfigurationPath OBJECT-TYPE
   SYNTAX         String
   ACCESS         read-write
   STATUS         mandatory
   DESCRIPTION    "The ConfigurationPath property indicates the path to the configuration files."
   REFERENCE      "Win32_BootConfiguration.ConfigurationPath"
::= { win32BootConfigurationEntry 3 }

win32BootConfigurationLastDrive OBJECT-TYPE
   SYNTAX         String
   ACCESS         read-write
   STATUS         mandatory
   DESCRIPTION    "The LastDrive property indicates the last drive letter to which a physical drive is assigned.<P>Example: Typically, the default setting is E."
   REFERENCE      "Win32_BootConfiguration.LastDrive"
::= { win32BootConfigurationEntry 4 }

win32BootConfigurationName OBJECT-TYPE
   SYNTAX         String
   ACCESS         read-write
   STATUS         mandatory
   DESCRIPTION    "The Name property indicates the name of the boot configuration."
   REFERENCE      "Win32_BootConfiguration.Name"
::= { win32BootConfigurationEntry 5 }

win32BootConfigurationScratchDirectory OBJECT-TYPE
   SYNTAX         String
   ACCESS         read-write
   STATUS         mandatory
   DESCRIPTION    "The ScratchDirectory property indicates the scratch directory of the Win32 boot configuration."
   REFERENCE      "Win32_BootConfiguration.ScratchDirectory"
::= { win32BootConfigurationEntry 6 }

win32BootConfigurationTempDirectory OBJECT-TYPE
   SYNTAX         String
   ACCESS         read-write
   STATUS         mandatory
   DESCRIPTION    "The TempDirectory property indicates the directory location where temporary files are stored.<P>Example: C:\\TEMP"
   REFERENCE      "Win32_BootConfiguration.TempDirectory"
::= { win32BootConfigurationEntry 7 }

win32DesktopTable OBJECT-TYPE
   SYNTAX         SEQUENCE OF Win32DesktopEntry
   ACCESS         not-accessible
   STATUS         mandatory
   DESCRIPTION    "The Win32_Desktop class represents the desktop layout of a Win32 system.<P>Example: The number and position of shortcuts on a Windows 95 or Windows NT workstation desktop"
   REFERENCE      "Win32_Desktop"
::= { win32WMI 480 }

win32DesktopEntry OBJECT-TYPE
   SYNTAX         Win32DesktopEntry
   ACCESS         not-accessible
   STATUS         mandatory
   DESCRIPTION    ""
   INDEX          { win32DesktopKeyIndex }
::= { win32DesktopTable 1 }

Win32DesktopEntry ::= SEQUENCE
{
   win32DesktopKeyIndex String,
   win32DesktopBorderWidth Uint32,
   win32DesktopCoolSwitch Boolean,
   win32DesktopCursorBlinkRate Uint32,
   win32DesktopDragFullWindows Boolean,
   win32DesktopGridGranularity Uint32,
   win32DesktopIconSpacing Uint32,
   win32DesktopIconTitleFaceName String,
   win32DesktopIconTitleSize Uint32,
   win32DesktopIconTitleWrap Boolean,
   win32DesktopName String,
   win32DesktopPattern String,
   win32DesktopScreenSaverActive Boolean,
   win32DesktopScreenSaverExecutable String,
   win32DesktopScreenSaverSecure Boolean,
   win32DesktopScreenSaverTimeout Uint32,
   win32DesktopWallpaper String,
   win32DesktopWallpaperTiled Boolean,
   win32DesktopWallpaperStretched Boolean
}

win32DesktopKeyIndex OBJECT-TYPE
   SYNTAX         String
   ACCESS         read-write
   STATUS         mandatory
   DESCRIPTION    ""
   REFERENCE      "Win32_Desktop.KeyIndex"
::= { win32DesktopEntry 1 }

win32DesktopBorderWidth OBJECT-TYPE
   SYNTAX         Uint32
   ACCESS         read-write
   STATUS         mandatory
   DESCRIPTION    "The BorderWidth property indicates the width of the desktop border.<P>Example: 1"
   REFERENCE      "Win32_Desktop.BorderWidth"
::= { win32DesktopEntry 2 }

win32DesktopCoolSwitch OBJECT-TYPE
   SYNTAX         Boolean
   ACCESS         read-write
   STATUS         mandatory
   DESCRIPTION    ""
   REFERENCE      "Win32_Desktop.CoolSwitch"
::= { win32DesktopEntry 3 }

win32DesktopCursorBlinkRate OBJECT-TYPE
   SYNTAX         Uint32
   ACCESS         read-write
   STATUS         mandatory
   DESCRIPTION    "The CursorBlinkRate property indicates the time (in milliseconds) between cursor blinks.<P>Example: 530"
   REFERENCE      "Win32_Desktop.CursorBlinkRate"
::= { win32DesktopEntry 4 }

win32DesktopDragFullWindows OBJECT-TYPE
   SYNTAX         Boolean
   ACCESS         read-write
   STATUS         mandatory
   DESCRIPTION    "The DragFullWindows property determines whether the full window is displayed while being dragged.<P>Values: TRUE or FALSE. If TRUE, the full window is displayed while being dragged."
   REFERENCE      "Win32_Desktop.DragFullWindows"
::= { win32DesktopEntry 5 }

win32DesktopGridGranularity OBJECT-TYPE
   SYNTAX         Uint32
   ACCESS         read-write
   STATUS         mandatory
   DESCRIPTION    "The GridGranularity property indicates the density of the desktop grid.<P>Example: 0"
   REFERENCE      "Win32_Desktop.GridGranularity"
::= { win32DesktopEntry 6 }

win32DesktopIconSpacing OBJECT-TYPE
   SYNTAX         Uint32
   ACCESS         read-write
   STATUS         mandatory
   DESCRIPTION    "The IconSpacing property indicates the spacing (in pixels) between icons.<P>Example: 75"
   REFERENCE      "Win32_Desktop.IconSpacing"
::= { win32DesktopEntry 7 }

win32DesktopIconTitleFaceName OBJECT-TYPE
   SYNTAX         String
   ACCESS         read-write
   STATUS         mandatory
   DESCRIPTION    "The IconTitleFaceName property indicates the name of the current desktop typeface (font).<P>Example: MS San Serif"
   REFERENCE      "Win32_Desktop.IconTitleFaceName"
::= { win32DesktopEntry 8 }

win32DesktopIconTitleSize OBJECT-TYPE
   SYNTAX         Uint32
   ACCESS         read-write
   STATUS         mandatory
   DESCRIPTION    "The IconTitleSize property indicates the title size of the icons.<P>Example: 9"
   REFERENCE      "Win32_Desktop.IconTitleSize"
::= { win32DesktopEntry 9 }

win32DesktopIconTitleWrap OBJECT-TYPE
   SYNTAX         Boolean
   ACCESS         read-write
   STATUS         mandatory
   DESCRIPTION    "The IconTitleWrap property determines whether the icon title text wraps to the next line.<P>Values: TRUE or FALSE. If TRUE, the title text wraps to the next line."
   REFERENCE      "Win32_Desktop.IconTitleWrap"
::= { win32DesktopEntry 10 }

win32DesktopName OBJECT-TYPE
   SYNTAX         String
   ACCESS         read-write
   STATUS         mandatory
   DESCRIPTION    "The Name property indicates the name of the current profile.<P>Example: MainProf"
   REFERENCE      "Win32_Desktop.Name"
::= { win32DesktopEntry 11 }

win32DesktopPattern OBJECT-TYPE
   SYNTAX         String
   ACCESS         read-write
   STATUS         mandatory
   DESCRIPTION    "The Pattern property indicates the desktop pattern."
   REFERENCE      "Win32_Desktop.Pattern"
::= { win32DesktopEntry 12 }

win32DesktopScreenSaverActive OBJECT-TYPE
   SYNTAX         Boolean
   ACCESS         read-write
   STATUS         mandatory
   DESCRIPTION    "The ScreenSaverActive property determines whether the screen saver is active.<P>Values: TRUE or FALSE. If TRUE, the screen saver is active."
   REFERENCE      "Win32_Desktop.ScreenSaverActive"
::= { win32DesktopEntry 13 }

win32DesktopScreenSaverExecutable OBJECT-TYPE
   SYNTAX         String
   ACCESS         read-write
   STATUS         mandatory
   DESCRIPTION    "The ScreenSaverExecutable property indicates name of the current screen saver executable file.<P>Example: LOGON.SCR"
   REFERENCE      "Win32_Desktop.ScreenSaverExecutable"
::= { win32DesktopEntry 14 }

win32DesktopScreenSaverSecure OBJECT-TYPE
   SYNTAX         Boolean
   ACCESS         read-write
   STATUS         mandatory
   DESCRIPTION    "The ScreenSaverSecure property determines whether the screen saver is password enabled.<P>Values: TRUE or FALSE. If TRUE, the screen saver is password enabled."
   REFERENCE      "Win32_Desktop.ScreenSaverSecure"
::= { win32DesktopEntry 15 }

win32DesktopScreenSaverTimeout OBJECT-TYPE
   SYNTAX         Uint32
   ACCESS         read-write
   STATUS         mandatory
   DESCRIPTION    "The ScreenSaverTimeout property indicates the amount of time before the screen saver takes effect."
   REFERENCE      "Win32_Desktop.ScreenSaverTimeout"
::= { win32DesktopEntry 16 }

win32DesktopWallpaper OBJECT-TYPE
   SYNTAX         String
   ACCESS         read-write
   STATUS         mandatory
   DESCRIPTION    "The Wallpaper property indicates the name of the wallpaper design.<P>Example: WINNT.BMP"
   REFERENCE      "Win32_Desktop.Wallpaper"
::= { win32DesktopEntry 17 }

win32DesktopWallpaperTiled OBJECT-TYPE
   SYNTAX         Boolean
   ACCESS         read-write
   STATUS         mandatory
   DESCRIPTION    "The WallpaperTiled property determines whether the wallpaper is tiled or centered.<P>Values: TRUE or FALSE. If TRUE, the wallpaper is tiled."
   REFERENCE      "Win32_Desktop.WallpaperTiled"
::= { win32DesktopEntry 18 }

win32DesktopWallpaperStretched OBJECT-TYPE
   SYNTAX         Boolean
   ACCESS         read-write
   STATUS         mandatory
   DESCRIPTION    "The WallpaperStretched property indicates whether the Stretch Wallpaper to Fit Screen option is set. This can only be true if the user has the Microsoft Plus package installed.<P>Values: TRUE and FALSE.  If TRUE, the Stretch Wallpaper to Fit Screen option is set. If Plus is not installed, this value is set to FALSE."
   REFERENCE      "Win32_Desktop.WallpaperStretched"
::= { win32DesktopEntry 19 }

win32DisplayConfigurationTable OBJECT-TYPE
   SYNTAX         SEQUENCE OF Win32DisplayConfigurationEntry
   ACCESS         not-accessible
   STATUS         mandatory
   DESCRIPTION    "The Win32_DisplayConfiguration class represents the display information of a Win32 system<P>Examples: Video adapter manufacturer, chipset version, display resolution, and number of colors"
   REFERENCE      "Win32_DisplayConfiguration"
::= { win32WMI 490 }

win32DisplayConfigurationEntry OBJECT-TYPE
   SYNTAX         Win32DisplayConfigurationEntry
   ACCESS         not-accessible
   STATUS         mandatory
   DESCRIPTION    ""
   INDEX          { win32DisplayConfigurationKeyIndex }
::= { win32DisplayConfigurationTable 1 }

Win32DisplayConfigurationEntry ::= SEQUENCE
{
   win32DisplayConfigurationKeyIndex String,
   win32DisplayConfigurationBitsPerPel Uint32,
   win32DisplayConfigurationDeviceName String,
   win32DisplayConfigurationDisplayFlags Uint32,
   win32DisplayConfigurationDisplayFrequency Uint32,
   win32DisplayConfigurationDitherType Uint32,
   win32DisplayConfigurationDriverVersion String,
   win32DisplayConfigurationICMIntent Uint32,
   win32DisplayConfigurationICMMethod Uint32,
   win32DisplayConfigurationLogPixels Uint32,
   win32DisplayConfigurationPelsHeight Uint32,
   win32DisplayConfigurationPelsWidth Uint32,
   win32DisplayConfigurationSpecificationVersion Uint32
}

win32DisplayConfigurationKeyIndex OBJECT-TYPE
   SYNTAX         String
   ACCESS         read-write
   STATUS         mandatory
   DESCRIPTION    ""
   REFERENCE      "Win32_DisplayConfiguration.KeyIndex"
::= { win32DisplayConfigurationEntry 1 }

win32DisplayConfigurationBitsPerPel OBJECT-TYPE
   SYNTAX         Uint32
   ACCESS         read-write
   STATUS         mandatory
   DESCRIPTION    "The BitsPerPel property indicates the number of bits required to represent the current state of a pixel.<P>Example: 8"
   REFERENCE      "Win32_DisplayConfiguration.BitsPerPel"
::= { win32DisplayConfigurationEntry 2 }

win32DisplayConfigurationDeviceName OBJECT-TYPE
   SYNTAX         String
   ACCESS         read-write
   STATUS         mandatory
   DESCRIPTION    "The DeviceName property indicates the name of the Win32 display device."
   REFERENCE      "Win32_DisplayConfiguration.DeviceName"
::= { win32DisplayConfigurationEntry 3 }

win32DisplayConfigurationDisplayFlags OBJECT-TYPE
   SYNTAX         Uint32
   ACCESS         read-write
   STATUS         mandatory
   DESCRIPTION    "The DisplayFlags property indicates the display flags of the Win32 display."
   REFERENCE      "Win32_DisplayConfiguration.DisplayFlags"
::= { win32DisplayConfigurationEntry 4 }

win32DisplayConfigurationDisplayFrequency OBJECT-TYPE
   SYNTAX         Uint32
   ACCESS         read-write
   STATUS         mandatory
   DESCRIPTION    "The DisplayFrequency property indicates the display frequency of the Win32 display."
   REFERENCE      "Win32_DisplayConfiguration.DisplayFrequency"
::= { win32DisplayConfigurationEntry 5 }

win32DisplayConfigurationDitherType OBJECT-TYPE
   SYNTAX         Uint32
   ACCESS         read-write
   STATUS         mandatory
   DESCRIPTION    "The DitherType property indicates the dither type of the Win32 display."
   REFERENCE      "Win32_DisplayConfiguration.DitherType"
::= { win32DisplayConfigurationEntry 6 }

win32DisplayConfigurationDriverVersion OBJECT-TYPE
   SYNTAX         String
   ACCESS         read-write
   STATUS         mandatory
   DESCRIPTION    "The DriverVersion property indicates the driver version of the Win32 display."
   REFERENCE      "Win32_DisplayConfiguration.DriverVersion"
::= { win32DisplayConfigurationEntry 7 }

win32DisplayConfigurationICMIntent OBJECT-TYPE
   SYNTAX         Uint32
   ACCESS         read-write
   STATUS         mandatory
   DESCRIPTION    ""
   REFERENCE      "Win32_DisplayConfiguration.ICMIntent"
::= { win32DisplayConfigurationEntry 8 }

win32DisplayConfigurationICMMethod OBJECT-TYPE
   SYNTAX         Uint32
   ACCESS         read-write
   STATUS         mandatory
   DESCRIPTION    ""
   REFERENCE      "Win32_DisplayConfiguration.ICMMethod"
::= { win32DisplayConfigurationEntry 9 }

win32DisplayConfigurationLogPixels OBJECT-TYPE
   SYNTAX         Uint32
   ACCESS         read-write
   STATUS         mandatory
   DESCRIPTION    ""
   REFERENCE      "Win32_DisplayConfiguration.LogPixels"
::= { win32DisplayConfigurationEntry 10 }

win32DisplayConfigurationPelsHeight OBJECT-TYPE
   SYNTAX         Uint32
   ACCESS         read-write
   STATUS         mandatory
   DESCRIPTION    ""
   REFERENCE      "Win32_DisplayConfiguration.PelsHeight"
::= { win32DisplayConfigurationEntry 11 }

win32DisplayConfigurationPelsWidth OBJECT-TYPE
   SYNTAX         Uint32
   ACCESS         read-write
   STATUS         mandatory
   DESCRIPTION    ""
   REFERENCE      "Win32_DisplayConfiguration.PelsWidth"
::= { win32DisplayConfigurationEntry 12 }

win32DisplayConfigurationSpecificationVersion OBJECT-TYPE
   SYNTAX         Uint32
   ACCESS         read-write
   STATUS         mandatory
   DESCRIPTION    "The SpecificationVersion property indicates the specification version of the Win32 display."
   REFERENCE      "Win32_DisplayConfiguration.SpecificationVersion"
::= { win32DisplayConfigurationEntry 13 }

win32DisplayControllerConfigurationTable OBJECT-TYPE
   SYNTAX         SEQUENCE OF Win32DisplayControllerConfigurationEntry
   ACCESS         not-accessible
   STATUS         mandatory
   DESCRIPTION    "The Win32_DisplayControllerConfiguration class represents the video adapter configuration information of a Win32 system.<P>Example: Jumper settings, Plug and Play information"
   REFERENCE      "Win32_DisplayControllerConfiguration"
::= { win32WMI 500 }

win32DisplayControllerConfigurationEntry OBJECT-TYPE
   SYNTAX         Win32DisplayControllerConfigurationEntry
   ACCESS         not-accessible
   STATUS         mandatory
   DESCRIPTION    ""
   INDEX          { win32DisplayControllerConfigurationKeyIndex }
::= { win32DisplayControllerConfigurationTable 1 }

Win32DisplayControllerConfigurationEntry ::= SEQUENCE
{
   win32DisplayControllerConfigurationKeyIndex String,
   win32DisplayControllerConfigurationBitsPerPixel Uint32,
   win32DisplayControllerConfigurationColorPlanes Uint32,
   win32DisplayControllerConfigurationDeviceEntriesInAColorTable Uint32,
   win32DisplayControllerConfigurationDeviceSpecificPens Uint32,
   win32DisplayControllerConfigurationHorizontalResolution Uint32,
   win32DisplayControllerConfigurationName String,
   win32DisplayControllerConfigurationRefreshRate Sint32,
   win32DisplayControllerConfigurationReservedSystemPaletteEntries Uint32,
   win32DisplayControllerConfigurationSystemPaletteEntries Uint32,
   win32DisplayControllerConfigurationVerticalResolution Uint32,
   win32DisplayControllerConfigurationVideoMode String      
}

win32DisplayControllerConfigurationKeyIndex OBJECT-TYPE
   SYNTAX         String
   ACCESS         read-write
   STATUS         mandatory
   DESCRIPTION    ""
   REFERENCE      "Win32_DisplayControllerConfiguration.KeyIndex"
::= { win32DisplayControllerConfigurationEntry 1 }

win32DisplayControllerConfigurationBitsPerPixel OBJECT-TYPE
   SYNTAX         Uint32
   ACCESS         read-write
   STATUS         mandatory
   DESCRIPTION    "The BitsPerPixel property indicates the current number of bits per pixel.<P>Example: 8"
   REFERENCE      "Win32_DisplayControllerConfiguration.BitsPerPixel"
::= { win32DisplayControllerConfigurationEntry 2 }

win32DisplayControllerConfigurationColorPlanes OBJECT-TYPE
   SYNTAX         Uint32
   ACCESS         read-write
   STATUS         mandatory
   DESCRIPTION    "The ColorPlanes property indicates the current number color panes in the display.<P>Example: 2"
   REFERENCE      "Win32_DisplayControllerConfiguration.ColorPlanes"
::= { win32DisplayControllerConfigurationEntry 3 }

win32DisplayControllerConfigurationDeviceEntriesInAColorTable OBJECT-TYPE
   SYNTAX         Uint32
   ACCESS         read-write
   STATUS         mandatory
   DESCRIPTION    "The DeviceEntriesInAColorTable property indicates the current number of device entries in a color table.<P>Example: 256"
   REFERENCE      "Win32_DisplayControllerConfiguration.DeviceEntriesInAColo"
::= { win32DisplayControllerConfigurationEntry 4 }

win32DisplayControllerConfigurationDeviceSpecificPens OBJECT-TYPE
   SYNTAX         Uint32
   ACCESS         read-write
   STATUS         mandatory
   DESCRIPTION    "The DeviceSpecificPens property indicates the current number of device-specific pens where 0xffff means the device does not support pens.<P>Example: 3"
   REFERENCE      "Win32_DisplayControllerConfiguration.DeviceSpecificPens"
::= { win32DisplayControllerConfigurationEntry 5 }

win32DisplayControllerConfigurationHorizontalResolution OBJECT-TYPE
   SYNTAX         Uint32
   ACCESS         read-write
   STATUS         mandatory
   DESCRIPTION    "The HorizontalResolution property indicates the current number of pixels in the horizontal direction (X axis) of the display.<P>Example: 1024"
   REFERENCE      "Win32_DisplayControllerConfiguration.HorizontalResolution"
::= { win32DisplayControllerConfigurationEntry 6 }

win32DisplayControllerConfigurationName OBJECT-TYPE
   SYNTAX         String
   ACCESS         read-write
   STATUS         mandatory
   DESCRIPTION    "The Name property indicates the name of the current resolution and color setting.<P>Example: 1024 x 768 with 256 colors"
   REFERENCE      "Win32_DisplayControllerConfiguration.Name"
::= { win32DisplayControllerConfigurationEntry 7 }

win32DisplayControllerConfigurationRefreshRate OBJECT-TYPE
   SYNTAX         Sint32
   ACCESS         read-write
   STATUS         mandatory
   DESCRIPTION    "The RefreshRate property indicates the refresh rate (in Hertz) of the video adapter.  0 or 1 indicate a default rate is being used.  A -1indicates that an optimal rate is being used.  <P>Example: 72"
   REFERENCE      "Win32_DisplayControllerConfiguration.RefreshRate"
::= { win32DisplayControllerConfigurationEntry 8 }

win32DisplayControllerConfigurationReservedSystemPaletteEntries OBJECT-TYPE
   SYNTAX         Uint32
   ACCESS         read-write
   STATUS         mandatory
   DESCRIPTION    "The ReservedSystemPaletteEntries property indicates the current number of reserved entries in a system palette.<P>Example: 24"
   REFERENCE      "Win32_DisplayControllerConfiguration.ReservedSystemPalett"
::= { win32DisplayControllerConfigurationEntry 9 }

win32DisplayControllerConfigurationSystemPaletteEntries OBJECT-TYPE
   SYNTAX         Uint32
   ACCESS         read-write
   STATUS         mandatory
   DESCRIPTION    "The SystemPaletteEntries property indicates the current number of entries in a system palette.<P>Example: 256"
   REFERENCE      "Win32_DisplayControllerConfiguration.SystemPaletteEntries"
::= { win32DisplayControllerConfigurationEntry 10 }

win32DisplayControllerConfigurationVerticalResolution OBJECT-TYPE
   SYNTAX         Uint32
   ACCESS         read-write
   STATUS         mandatory
   DESCRIPTION    "The VerticalResolution property indicates the current number of pixels in the vertical direction (Y axis) of the display.<P>Example: 768"
   REFERENCE      "Win32_DisplayControllerConfiguration.VerticalResolution"
::= { win32DisplayControllerConfigurationEntry 11 }

win32DisplayControllerConfigurationVideoMode OBJECT-TYPE
   SYNTAX         String
   ACCESS         read-write
   STATUS         mandatory
   DESCRIPTION    "The VideoMode property indicates the current pixel resolution and color setting of the display.<P>Example: 1024 X 768 with 256 colors."
   REFERENCE      "Win32_DisplayControllerConfiguration.VideoMode"
::= { win32DisplayControllerConfigurationEntry 12 }

win32LogicalMemoryConfigurationTable OBJECT-TYPE
   SYNTAX         SEQUENCE OF Win32LogicalMemoryConfigurationEntry
   ACCESS         not-accessible
   STATUS         mandatory
   DESCRIPTION    "The Win32_LogicalMemoryConfiguration class represents the logical memory configuration on a Win32 system."
   REFERENCE      "Win32_LogicalMemoryConfiguration"
::= { win32WMI 510 }

win32LogicalMemoryConfigurationEntry OBJECT-TYPE
   SYNTAX         Win32LogicalMemoryConfigurationEntry
   ACCESS         not-accessible
   STATUS         mandatory
   DESCRIPTION    ""
   INDEX          { win32LogicalMemoryConfigurationKeyIndex }
::= { win32LogicalMemoryConfigurationTable 1 }

Win32LogicalMemoryConfigurationEntry ::= SEQUENCE
{
   win32LogicalMemoryConfigurationKeyIndex String,
   win32LogicalMemoryConfigurationAvailableVirtualMemory Uint32,
   win32LogicalMemoryConfigurationName String,
   win32LogicalMemoryConfigurationTotalPageFileSpace Uint32,
   win32LogicalMemoryConfigurationTotalPhysicalMemory Uint32,
   win32LogicalMemoryConfigurationTotalVirtualMemory Uint32
}

win32LogicalMemoryConfigurationKeyIndex OBJECT-TYPE
   SYNTAX         String
   ACCESS         read-write
   STATUS         mandatory
   DESCRIPTION    ""
   REFERENCE      "Win32_LogicalMemoryConfiguration.KeyIndex"
::= { win32LogicalMemoryConfigurationEntry 1 }

win32LogicalMemoryConfigurationAvailableVirtualMemory OBJECT-TYPE
   SYNTAX         Uint32
   ACCESS         read-write
   STATUS         mandatory
   DESCRIPTION    "The AvailableVirtualMemory property indicates the size (in bytes) of the available virtual memory.<P>Example: 2052288"
   REFERENCE      "Win32_LogicalMemoryConfiguration.AvailableVirtualMemory"
::= { win32LogicalMemoryConfigurationEntry 2 }

win32LogicalMemoryConfigurationName OBJECT-TYPE
   SYNTAX         String
   ACCESS         read-write
   STATUS         mandatory
   DESCRIPTION    "The Name property indicates the name of the logical memory configuration."
   REFERENCE      "Win32_LogicalMemoryConfiguration.Name"
::= { win32LogicalMemoryConfigurationEntry 3 }

win32LogicalMemoryConfigurationTotalPageFileSpace OBJECT-TYPE
   SYNTAX         Uint32
   ACCESS         read-write
   STATUS         mandatory
   DESCRIPTION    "The TotalPageFileSpace property indicates the total size (in bytes) of the page file.<P>Example: 524160"
   REFERENCE      "Win32_LogicalMemoryConfiguration.TotalPageFileSpace"
::= { win32LogicalMemoryConfigurationEntry 4 }

win32LogicalMemoryConfigurationTotalPhysicalMemory OBJECT-TYPE
   SYNTAX         Uint32
   ACCESS         read-write
   STATUS         mandatory
   DESCRIPTION    "The TotalPhysicalMemory property indicates the total size (in bytes) of the physical memory.<P>Example: 40464"
   REFERENCE      "Win32_LogicalMemoryConfiguration.TotalPhysicalMemory"
::= { win32LogicalMemoryConfigurationEntry 5 }

win32LogicalMemoryConfigurationTotalVirtualMemory OBJECT-TYPE
   SYNTAX         Uint32
   ACCESS         read-write
   STATUS         mandatory
   DESCRIPTION    "The TotalVirtualMemory property indicates the total size (in bytes) of the virtual memory.<P>Example: 2093056"
   REFERENCE      "Win32_LogicalMemoryConfiguration.TotalVirtualMemory"
::= { win32LogicalMemoryConfigurationEntry 6 }

win32NetworkLoginProfileTable OBJECT-TYPE
   SYNTAX         SEQUENCE OF Win32NetworkLoginProfileEntry
   ACCESS         not-accessible
   STATUS         mandatory
   DESCRIPTION    "The Win32_NetworkLoginProfile class represents the network login information of a particular user on a Win32 system."
   REFERENCE      "Win32_NetworkLoginProfile"
::= { win32WMI 520 }

win32NetworkLoginProfileEntry OBJECT-TYPE
   SYNTAX         Win32NetworkLoginProfileEntry
   ACCESS         not-accessible
   STATUS         mandatory
   DESCRIPTION    ""
   INDEX          { win32NetworkLoginProfileKeyIndex }
::= { win32NetworkLoginProfileTable 1 }

Win32NetworkLoginProfileEntry ::= SEQUENCE
{
   win32NetworkLoginProfileKeyIndex String,
   win32NetworkLoginProfileAccountExpires Datetime,
   win32NetworkLoginProfileAuthorizationFlags Uint32,
   win32NetworkLoginProfileBadPasswordCount Uint32,
   win32NetworkLoginProfileCodePage Uint32,
   win32NetworkLoginProfileComment String,
   win32NetworkLoginProfileCountryCode Uint32,
   win32NetworkLoginProfileFlags Uint32,
   win32NetworkLoginProfileFullName String,
   win32NetworkLoginProfileHomeDirectory String,
   win32NetworkLoginProfileHomeDirectoryDrive String,
   win32NetworkLoginProfileLastLogoff Datetime,
   win32NetworkLoginProfileLastLogon Datetime,
   win32NetworkLoginProfileLogonHours String,
   win32NetworkLoginProfileLogonServer String,
   win32NetworkLoginProfileMaximumStorage String,
   win32NetworkLoginProfileName String,
   win32NetworkLoginProfileNumberOfLogons Uint32,
   win32NetworkLoginProfileParameters String,
   win32NetworkLoginProfilePasswordAge Datetime,
   win32NetworkLoginProfilePasswordExpires Datetime,
   win32NetworkLoginProfilePrimaryGroupId Uint32,
   win32NetworkLoginProfilePrivileges Uint32,
   win32NetworkLoginProfileProfile String,
   win32NetworkLoginProfileScriptPath String,
   win32NetworkLoginProfileUnitsPerWeek Uint32,
   win32NetworkLoginProfileUserComment String,
   win32NetworkLoginProfileUserId Uint32,
   win32NetworkLoginProfileUserType String,
   win32NetworkLoginProfileWorkstations String
}

win32NetworkLoginProfileKeyIndex OBJECT-TYPE
   SYNTAX         String
   ACCESS         read-write
   STATUS         mandatory
   DESCRIPTION    ""
   REFERENCE      "Win32_NetworkLoginProfile.KeyIndex"
::= { win32NetworkLoginProfileEntry 1 }

win32NetworkLoginProfileAccountExpires OBJECT-TYPE
   SYNTAX         Datetime
   ACCESS         read-write
   STATUS         mandatory
   DESCRIPTION    "The AccountExpires property indicates the date and time the account of a particular user expires.<P>Example: 20521201000230.000000000"
   REFERENCE      "Win32_NetworkLoginProfile.AccountExpires"
::= { win32NetworkLoginProfileEntry 2 }

win32NetworkLoginProfileAuthorizationFlags OBJECT-TYPE
   SYNTAX         Uint32
   ACCESS         read-write
   STATUS         mandatory
   DESCRIPTION    ""
   REFERENCE      "Win32_NetworkLoginProfile.AuthorizationFlags"
::= { win32NetworkLoginProfileEntry 3 }

win32NetworkLoginProfileBadPasswordCount OBJECT-TYPE
   SYNTAX         Uint32
   ACCESS         read-write
   STATUS         mandatory
   DESCRIPTION    "The BadPasswordCount property indicates the number of times the user enters a bad password when logging on to a Win32 system.<P>Example: 0"
   REFERENCE      "Win32_NetworkLoginProfile.BadPasswordCount"
::= { win32NetworkLoginProfileEntry 4 }

win32NetworkLoginProfileCodePage OBJECT-TYPE
   SYNTAX         Uint32
   ACCESS         read-write
   STATUS         mandatory
   DESCRIPTION    "The CodePage property indicates the code page of the Win32 network login profile."
   REFERENCE      "Win32_NetworkLoginProfile.CodePage"
::= { win32NetworkLoginProfileEntry 5 }

win32NetworkLoginProfileComment OBJECT-TYPE
   SYNTAX         String
   ACCESS         read-write
   STATUS         mandatory
   DESCRIPTION    "The Comment property indicates a comment."
   REFERENCE      "Win32_NetworkLoginProfile.Comment"
::= { win32NetworkLoginProfileEntry 6 }

win32NetworkLoginProfileCountryCode OBJECT-TYPE
   SYNTAX         Uint32
   ACCESS         read-write
   STATUS         mandatory
   DESCRIPTION    "The CountryCode property indicates the country of the user."
   REFERENCE      "Win32_NetworkLoginProfile.CountryCode"
::= { win32NetworkLoginProfileEntry 7 }

win32NetworkLoginProfileFlags OBJECT-TYPE
   SYNTAX         Uint32
   ACCESS         read-write
   STATUS         mandatory
   DESCRIPTION    "The Flags property indicates the flags used in the NetWorkLoginProfile."
   REFERENCE      "Win32_NetworkLoginProfile.Flags"
::= { win32NetworkLoginProfileEntry 8 }

win32NetworkLoginProfileFullName OBJECT-TYPE
   SYNTAX         String
   ACCESS         read-write
   STATUS         mandatory
   DESCRIPTION    "The FullName property indicates the full name of the user belonging to the network login profile."
   REFERENCE      "Win32_NetworkLoginProfile.FullName"
::= { win32NetworkLoginProfileEntry 9 }

win32NetworkLoginProfileHomeDirectory OBJECT-TYPE
   SYNTAX         String
   ACCESS         read-write
   STATUS         mandatory
   DESCRIPTION    "The HomeDirectory property indicates the home directory of the user.<P>Example: \\HOMEDIR"
   REFERENCE      "Win32_NetworkLoginProfile.HomeDirectory"
::= { win32NetworkLoginProfileEntry 10 }

win32NetworkLoginProfileHomeDirectoryDrive OBJECT-TYPE
   SYNTAX         String
   ACCESS         read-write
   STATUS         mandatory
   DESCRIPTION    "The HomeDirectoryDrive property indicates the drive of the user's home directory.<P>Example: C:"
   REFERENCE      "Win32_NetworkLoginProfile.HomeDirectoryDrive"
::= { win32NetworkLoginProfileEntry 11 }

win32NetworkLoginProfileLastLogoff OBJECT-TYPE
   SYNTAX         Datetime
   ACCESS         read-write
   STATUS         mandatory
   DESCRIPTION    "The LastLogoff property indicates the date and time the user last logged off the system.<P>Example: 19521201000230.000000000"
   REFERENCE      "Win32_NetworkLoginProfile.LastLogoff"
::= { win32NetworkLoginProfileEntry 12 }

win32NetworkLoginProfileLastLogon OBJECT-TYPE
   SYNTAX         Datetime
   ACCESS         read-write
   STATUS         mandatory
   DESCRIPTION    "The LastLogon property indicates the date and time the user last logged on to the system.<P>Example: 19521201000230.000000000"
   REFERENCE      "Win32_NetworkLoginProfile.LastLogon"
::= { win32NetworkLoginProfileEntry 13 }

win32NetworkLoginProfileLogonHours OBJECT-TYPE
   SYNTAX         String
   ACCESS         read-write
   STATUS         mandatory
   DESCRIPTION    "The LogonHours property is a string that specifies the times during which the user can log on."
   REFERENCE      "Win32_NetworkLoginProfile.LogonHours"
::= { win32NetworkLoginProfileEntry 14 }

win32NetworkLoginProfileLogonServer OBJECT-TYPE
   SYNTAX         String
   ACCESS         read-write
   STATUS         mandatory
   DESCRIPTION    "The LogonServer property indicates the name of the server onto which the user has logged.<P>Example: OCEANIA"
   REFERENCE      "Win32_NetworkLoginProfile.LogonServer"
::= { win32NetworkLoginProfileEntry 15 }

win32NetworkLoginProfileMaximumStorage OBJECT-TYPE
   SYNTAX         String
   ACCESS         read-write
   STATUS         mandatory
   DESCRIPTION    "The MaximumStorage property indicates the maximum storage space that can be allocated to this user.<P>Example: 10000000"
   REFERENCE      "Win32_NetworkLoginProfile.MaximumStorage"
::= { win32NetworkLoginProfileEntry 16 }

win32NetworkLoginProfileName OBJECT-TYPE
   SYNTAX         String
   ACCESS         read-write
   STATUS         mandatory
   DESCRIPTION    "The Name property indicates the name of the user.<P>Example: Joe Bloggs"
   REFERENCE      "Win32_NetworkLoginProfile.Name"
::= { win32NetworkLoginProfileEntry 17 }

win32NetworkLoginProfileNumberOfLogons OBJECT-TYPE
   SYNTAX         Uint32
   ACCESS         read-write
   STATUS         mandatory
   DESCRIPTION    "The NumberOfLogons property indicates the number of logons at any given time.<P>Example: 4"
   REFERENCE      "Win32_NetworkLoginProfile.NumberOfLogons"
::= { win32NetworkLoginProfileEntry 18 }

win32NetworkLoginProfileParameters OBJECT-TYPE
   SYNTAX         String
   ACCESS         read-write
   STATUS         mandatory
   DESCRIPTION    "The Parameters property indicates the parameters used in the NetWorkLoginProfile."
   REFERENCE      "Win32_NetworkLoginProfile.Parameters"
::= { win32NetworkLoginProfileEntry 19 }

win32NetworkLoginProfilePasswordAge OBJECT-TYPE
   SYNTAX         Datetime
   ACCESS         read-write
   STATUS         mandatory
   DESCRIPTION    "The PasswordAge property indicates the length of time a password has been in effect.<P>Example: 00001201000230.000000000"
   REFERENCE      "Win32_NetworkLoginProfile.PasswordAge"
::= { win32NetworkLoginProfileEntry 20 }

win32NetworkLoginProfilePasswordExpires OBJECT-TYPE
   SYNTAX         Datetime
   ACCESS         read-write
   STATUS         mandatory
   DESCRIPTION    "The PasswordExpires property indicates date and time the password expires.<P>Example: 19521201000230.000000000"
   REFERENCE      "Win32_NetworkLoginProfile.PasswordExpires"
::= { win32NetworkLoginProfileEntry 21 }

win32NetworkLoginProfilePrimaryGroupId OBJECT-TYPE
   SYNTAX         Uint32
   ACCESS         read-write
   STATUS         mandatory
   DESCRIPTION    "The PrimaryGroupID property indicates the ID of the primary group in the NetworkLoginProfile."
   REFERENCE      "Win32_NetworkLoginProfile.PrimaryGroupId"
::= { win32NetworkLoginProfileEntry 22 }

win32NetworkLoginProfilePrivileges OBJECT-TYPE
   SYNTAX         Uint32
   ACCESS         read-write
   STATUS         mandatory
   DESCRIPTION    "The privileges property indicates user privileges allowed for the NetworkLoginProfile."
   REFERENCE      "Win32_NetworkLoginProfile.Privileges"
::= { win32NetworkLoginProfileEntry 23 }

win32NetworkLoginProfileProfile OBJECT-TYPE
   SYNTAX         String
   ACCESS         read-write
   STATUS         mandatory
   DESCRIPTION    "The Profile property contains information about the user.<P>Example: Administrator"
   REFERENCE      "Win32_NetworkLoginProfile.Profile"
::= { win32NetworkLoginProfileEntry 24 }

win32NetworkLoginProfileScriptPath OBJECT-TYPE
   SYNTAX         String
   ACCESS         read-write
   STATUS         mandatory
   DESCRIPTION    "The ScriptPath property indicates the path to the user's logon script.<P>Example: C:\\win\\profiles\\JoeBloggs"
   REFERENCE      "Win32_NetworkLoginProfile.ScriptPath"
::= { win32NetworkLoginProfileEntry 25 }

win32NetworkLoginProfileUnitsPerWeek OBJECT-TYPE
   SYNTAX         Uint32
   ACCESS         read-write
   STATUS         mandatory
   DESCRIPTION    "The UnitsPerWeek property indicates the units used each week in the NetworkLoginProfile."
   REFERENCE      "Win32_NetworkLoginProfile.UnitsPerWeek"
::= { win32NetworkLoginProfileEntry 26 }

win32NetworkLoginProfileUserComment OBJECT-TYPE
   SYNTAX         String
   ACCESS         read-write
   STATUS         mandatory
   DESCRIPTION    "The UserComment property indicates comments by users."
   REFERENCE      "Win32_NetworkLoginProfile.UserComment"
::= { win32NetworkLoginProfileEntry 27 }

win32NetworkLoginProfileUserId OBJECT-TYPE
   SYNTAX         Uint32
   ACCESS         read-write
   STATUS         mandatory
   DESCRIPTION    "The UserId property indicates the name or logon alias of the user."
   REFERENCE      "Win32_NetworkLoginProfile.UserId"
::= { win32NetworkLoginProfileEntry 28 }

win32NetworkLoginProfileUserType OBJECT-TYPE
   SYNTAX         String
   ACCESS         read-write
   STATUS         mandatory
   DESCRIPTION    "The UserType property indicates types of users."
   REFERENCE      "Win32_NetworkLoginProfile.UserType"
::= { win32NetworkLoginProfileEntry 29 }

win32NetworkLoginProfileWorkstations OBJECT-TYPE
   SYNTAX         String
   ACCESS         read-write
   STATUS         mandatory
   DESCRIPTION    "The Workstations property indicates the workstations used in the NetworkLoginProfile."
   REFERENCE      "Win32_NetworkLoginProfile.Workstations"
::= { win32NetworkLoginProfileEntry 30 }

win32OSRecoveryConfigurationTable OBJECT-TYPE
   SYNTAX         SEQUENCE OF Win32OSRecoveryConfigurationEntry
   ACCESS         not-accessible
   STATUS         mandatory
   DESCRIPTION    "The Win32_OSRecoveryConfiguration class represents the configuration information necessary to recover from an operating system failure, such as a boot failure or system crash."
   REFERENCE      "Win32_OSRecoveryConfiguration"
::= { win32WMI 530 }

win32OSRecoveryConfigurationEntry OBJECT-TYPE
   SYNTAX         Win32OSRecoveryConfigurationEntry
   ACCESS         not-accessible
   STATUS         mandatory
   DESCRIPTION    ""
   INDEX          { win32OSRecoveryConfigurationKeyIndex }
::= { win32OSRecoveryConfigurationTable 1 }

Win32OSRecoveryConfigurationEntry ::= SEQUENCE
{
   win32OSRecoveryConfigurationKeyIndex String,
   win32OSRecoveryConfigurationAutoReboot Boolean,
   win32OSRecoveryConfigurationDebugFilePath String,
   win32OSRecoveryConfigurationName String,
   win32OSRecoveryConfigurationOverwriteExistingDebugFile Boolean,
   win32OSRecoveryConfigurationSendAdminAlert Boolean,
   win32OSRecoveryConfigurationWriteDebugInfo Boolean,
   win32OSRecoveryConfigurationWriteToSystemLog Boolean
}

win32OSRecoveryConfigurationKeyIndex OBJECT-TYPE
   SYNTAX         String
   ACCESS         read-write
   STATUS         mandatory
   DESCRIPTION    ""
   REFERENCE      "Win32_OSRecoveryConfiguration.KeyIndex"
::= { win32OSRecoveryConfigurationEntry 1 }

win32OSRecoveryConfigurationAutoReboot OBJECT-TYPE
   SYNTAX         Boolean
   ACCESS         read-write
   STATUS         mandatory
   DESCRIPTION    "The AutoReboot property determines whether the system will be rebooted automatically during a recovery operation.<P>Values: TRUE or FALSE. If TRUE, the system will be automatically rebooted."
   REFERENCE      "Win32_OSRecoveryConfiguration.AutoReboot"
::= { win32OSRecoveryConfigurationEntry 2 }

win32OSRecoveryConfigurationDebugFilePath OBJECT-TYPE
   SYNTAX         String
   ACCESS         read-write
   STATUS         mandatory
   DESCRIPTION    "The DebugFilePath property indicates the full path to the debug file."
   REFERENCE      "Win32_OSRecoveryConfiguration.DebugFilePath"
::= { win32OSRecoveryConfigurationEntry 3 }

win32OSRecoveryConfigurationName OBJECT-TYPE
   SYNTAX         String
   ACCESS         read-write
   STATUS         mandatory
   DESCRIPTION    "The Name property indicates the name used in the OSRecoveryConfiguration."
   REFERENCE      "Win32_OSRecoveryConfiguration.Name"
::= { win32OSRecoveryConfigurationEntry 4 }

win32OSRecoveryConfigurationOverwriteExistingDebugFile OBJECT-TYPE
   SYNTAX         Boolean
   ACCESS         read-write
   STATUS         mandatory
   DESCRIPTION    "The OverwriteExistingDebugFile property determines whether to overwrite an existing debug file. This property is valid only if the WriteDebugInfo property is set to TRUE.<P>Values: TRUE or FALSE. If TRUE, the existing debug file will be overwritten."
   REFERENCE      "Win32_OSRecoveryConfiguration.OverwriteExistingDebugFile"
::= { win32OSRecoveryConfigurationEntry 5 }

win32OSRecoveryConfigurationSendAdminAlert OBJECT-TYPE
   SYNTAX         Boolean
   ACCESS         read-write
   STATUS         mandatory
   DESCRIPTION    "The SendAdminAlert property determines whether an alert message will be sent to the system administrator in the event of an operating system failure.<P>Values: TRUE or FALSE. If TRUE, the system will send an alert to the system administrator."
   REFERENCE      "Win32_OSRecoveryConfiguration.SendAdminAlert"
::= { win32OSRecoveryConfigurationEntry 6 }

win32OSRecoveryConfigurationWriteDebugInfo OBJECT-TYPE
   SYNTAX         Boolean
   ACCESS         read-write
   STATUS         mandatory
   DESCRIPTION    "The WriteDebugInfo property determines whether debug information will be written to a file.<P>Values: TRUE or FALSE. If TRUE, debug info is written a file."
   REFERENCE      "Win32_OSRecoveryConfiguration.WriteDebugInfo"
::= { win32OSRecoveryConfigurationEntry 7 }

win32OSRecoveryConfigurationWriteToSystemLog OBJECT-TYPE
   SYNTAX         Boolean
   ACCESS         read-write
   STATUS         mandatory
   DESCRIPTION    "The WriteToSystemLog property determines whether system failure information will be written to a system log file.<P>Values: TRUE or FALSE. If TRUE, system failure information will be written to a system log file."
   REFERENCE      "Win32_OSRecoveryConfiguration.WriteToSystemLog"
::= { win32OSRecoveryConfigurationEntry 8 }

win32PrinterConfigurationTable OBJECT-TYPE
   SYNTAX         SEQUENCE OF Win32PrinterConfigurationEntry
   ACCESS         not-accessible
   STATUS         mandatory
   DESCRIPTION    "The Win32_PrinterConfiguration class defines a printer configuration."
   REFERENCE      "Win32_PrinterConfiguration"
::= { win32WMI 540 }

win32PrinterConfigurationEntry OBJECT-TYPE
   SYNTAX         Win32PrinterConfigurationEntry
   ACCESS         not-accessible
   STATUS         mandatory
   DESCRIPTION    ""
   INDEX          { win32PrinterConfigurationKeyIndex }
::= { win32PrinterConfigurationTable 1 }

Win32PrinterConfigurationEntry ::= SEQUENCE
{
   win32PrinterConfigurationKeyIndex String,
   win32PrinterConfigurationBitsPerPel Uint32,
   win32PrinterConfigurationCollate Boolean,
   win32PrinterConfigurationColor Uint32,
   win32PrinterConfigurationCopies Uint32,
   win32PrinterConfigurationDeviceName String,
   win32PrinterConfigurationDisplayFlags Uint32,
   win32PrinterConfigurationDisplayFrequency Uint32,
   win32PrinterConfigurationDitherType Uint32,
   win32PrinterConfigurationDriverVersion Uint32,
   win32PrinterConfigurationDuplex Boolean,
   win32PrinterConfigurationFormName String,
   win32PrinterConfigurationICMIntent Uint32,
   win32PrinterConfigurationICMMethod Uint32,
   win32PrinterConfigurationLogPixels Uint32,
   win32PrinterConfigurationMediaType Uint32,
   win32PrinterConfigurationName String,
   win32PrinterConfigurationOrientation Uint32,
   win32PrinterConfigurationPaperLength Uint32,
   win32PrinterConfigurationPaperSize String,
   win32PrinterConfigurationPaperWidth Uint32,
   win32PrinterConfigurationPelsHeight Uint32,
   win32PrinterConfigurationPelsWidth Uint32,
   win32PrinterConfigurationPrintQuality Uint32,
   win32PrinterConfigurationScale Uint32,
   win32PrinterConfigurationSpecificationVersion Uint32,
   win32PrinterConfigurationTTOption Uint32,
   win32PrinterConfigurationXResolution Uint32,
   win32PrinterConfigurationYResolution Uint32
}

win32PrinterConfigurationKeyIndex OBJECT-TYPE
   SYNTAX         String
   ACCESS         read-write
   STATUS         mandatory
   DESCRIPTION    ""
   REFERENCE      "Win32_PrinterConfiguration.KeyIndex"
::= { win32PrinterConfigurationEntry 1 }

win32PrinterConfigurationBitsPerPel OBJECT-TYPE
   SYNTAX         Uint32
   ACCESS         read-write
   STATUS         mandatory
   DESCRIPTION    "The BitsPerPel property indicates the number of bits per pixel for the Win32 printer.<P>Example: 16"
   REFERENCE      "Win32_PrinterConfiguration.BitsPerPel"
::= { win32PrinterConfigurationEntry 2 }

win32PrinterConfigurationCollate OBJECT-TYPE
   SYNTAX         Boolean
   ACCESS         read-write
   STATUS         mandatory
   DESCRIPTION    "The Collate property determines whether to collate the print job.<P>Values: TRUE or FALSE. If TRUE, the printer collates the print job."
   REFERENCE      "Win32_PrinterConfiguration.Collate"
::= { win32PrinterConfigurationEntry 3 }

win32PrinterConfigurationColor OBJECT-TYPE
   SYNTAX         Uint32
   ACCESS         read-write
   STATUS         mandatory
   DESCRIPTION    "The Color property indicates the color in which print jobs are produced.<P>Example: 0x000"
   REFERENCE      "Win32_PrinterConfiguration.Color"
::= { win32PrinterConfigurationEntry 4 }

win32PrinterConfigurationCopies OBJECT-TYPE
   SYNTAX         Uint32
   ACCESS         read-write
   STATUS         mandatory
   DESCRIPTION    "The Copies property indicates the number copies to be printed.<P>Example: 2"
   REFERENCE      "Win32_PrinterConfiguration.Copies"
::= { win32PrinterConfigurationEntry 5 }

win32PrinterConfigurationDeviceName OBJECT-TYPE
   SYNTAX         String
   ACCESS         read-write
   STATUS         mandatory
   DESCRIPTION    "The DeviceName property indicates the name of the print device."
   REFERENCE      "Win32_PrinterConfiguration.DeviceName"
::= { win32PrinterConfigurationEntry 6 }

win32PrinterConfigurationDisplayFlags OBJECT-TYPE
   SYNTAX         Uint32
   ACCESS         read-write
   STATUS         mandatory
   DESCRIPTION    "The DisplayFlags property indicates the display flags for the Win32 printer."
   REFERENCE      "Win32_PrinterConfiguration.DisplayFlags"
::= { win32PrinterConfigurationEntry 7 }

win32PrinterConfigurationDisplayFrequency OBJECT-TYPE
   SYNTAX         Uint32
   ACCESS         read-write
   STATUS         mandatory
   DESCRIPTION    "The DisplayFrequency property indicates the display frequency for the Win32 printer."
   REFERENCE      "Win32_PrinterConfiguration.DisplayFrequency"
::= { win32PrinterConfigurationEntry 8 }

win32PrinterConfigurationDitherType OBJECT-TYPE
   SYNTAX         Uint32
   ACCESS         read-write
   STATUS         mandatory
   DESCRIPTION    "The DitherType property indicates the dither type for the Win32 printer."
   REFERENCE      "Win32_PrinterConfiguration.DitherType"
::= { win32PrinterConfigurationEntry 9 }

win32PrinterConfigurationDriverVersion OBJECT-TYPE
   SYNTAX         Uint32
   ACCESS         read-write
   STATUS         mandatory
   DESCRIPTION    "The DriverVersion property indicates the version of the Win32 printer driver."
   REFERENCE      "Win32_PrinterConfiguration.DriverVersion"
::= { win32PrinterConfigurationEntry 10 }

win32PrinterConfigurationDuplex OBJECT-TYPE
   SYNTAX         Boolean
   ACCESS         read-write
   STATUS         mandatory
   DESCRIPTION    "The Duplex property determines whether the print media is printed on both sides.<P>Values: TRUE or FALSE. If TRUE, the print media is printed on both sides."
   REFERENCE      "Win32_PrinterConfiguration.Duplex"
::= { win32PrinterConfigurationEntry 11 }

win32PrinterConfigurationFormName OBJECT-TYPE
   SYNTAX         String
   ACCESS         read-write
   STATUS         mandatory
   DESCRIPTION    "The FormName property indicates the name of the form used for the print job.<P>Example: Cheques"
   REFERENCE      "Win32_PrinterConfiguration.FormName"
::= { win32PrinterConfigurationEntry 12 }

win32PrinterConfigurationICMIntent OBJECT-TYPE
   SYNTAX         Uint32
   ACCESS         read-write
   STATUS         mandatory
   DESCRIPTION    ""
   REFERENCE      "Win32_PrinterConfiguration.ICMIntent"
::= { win32PrinterConfigurationEntry 13 }

win32PrinterConfigurationICMMethod OBJECT-TYPE
   SYNTAX         Uint32
   ACCESS         read-write
   STATUS         mandatory
   DESCRIPTION    ""
   REFERENCE      "Win32_PrinterConfiguration.ICMMethod"
::= { win32PrinterConfigurationEntry 14 }

win32PrinterConfigurationLogPixels OBJECT-TYPE
   SYNTAX         Uint32
   ACCESS         read-write
   STATUS         mandatory
   DESCRIPTION    ""
   REFERENCE      "Win32_PrinterConfiguration.LogPixels"
::= { win32PrinterConfigurationEntry 15 }

win32PrinterConfigurationMediaType OBJECT-TYPE
   SYNTAX         Uint32
   ACCESS         read-write
   STATUS         mandatory
   DESCRIPTION    "The MediaType property indicates the media type.<P>Example: Paper"
   REFERENCE      "Win32_PrinterConfiguration.MediaType"
::= { win32PrinterConfigurationEntry 16 }

win32PrinterConfigurationName OBJECT-TYPE
   SYNTAX         String
   ACCESS         read-write
   STATUS         mandatory
   DESCRIPTION    "The Name property indicates the name of the current printer configuration.<P>Character Set: Alphanumeric"
   REFERENCE      "Win32_PrinterConfiguration.Name"
::= { win32PrinterConfigurationEntry 17 }

win32PrinterConfigurationOrientation OBJECT-TYPE
   SYNTAX         Uint32
   ACCESS         read-write
   STATUS         mandatory
   DESCRIPTION    "The Orientation property indicates the orientation of the print job.<P>Example: Landscape or Portrait"
   REFERENCE      "Win32_PrinterConfiguration.Orientation"
::= { win32PrinterConfigurationEntry 18 }

win32PrinterConfigurationPaperLength OBJECT-TYPE
   SYNTAX         Uint32
   ACCESS         read-write
   STATUS         mandatory
   DESCRIPTION    "The PaperLength property indicates the length of the paper.<P>Example: 11"
   REFERENCE      "Win32_PrinterConfiguration.PaperLength"
::= { win32PrinterConfigurationEntry 19 }

win32PrinterConfigurationPaperSize OBJECT-TYPE
   SYNTAX         String
   ACCESS         read-write
   STATUS         mandatory
   DESCRIPTION    "The PaperSize property indicates the size of the paper.<P>Example: A4 or Letter"
   REFERENCE      "Win32_PrinterConfiguration.PaperSize"
::= { win32PrinterConfigurationEntry 20 }

win32PrinterConfigurationPaperWidth OBJECT-TYPE
   SYNTAX         Uint32
   ACCESS         read-write
   STATUS         mandatory
   DESCRIPTION    "The PaperWidth property indicates the width of the paper.<P>Example: 8.5"
   REFERENCE      "Win32_PrinterConfiguration.PaperWidth"
::= { win32PrinterConfigurationEntry 21 }

win32PrinterConfigurationPelsHeight OBJECT-TYPE
   SYNTAX         Uint32
   ACCESS         read-write
   STATUS         mandatory
   DESCRIPTION    ""
   REFERENCE      "Win32_PrinterConfiguration.PelsHeight"
::= { win32PrinterConfigurationEntry 22 }

win32PrinterConfigurationPelsWidth OBJECT-TYPE
   SYNTAX         Uint32
   ACCESS         read-write
   STATUS         mandatory
   DESCRIPTION    ""
   REFERENCE      "Win32_PrinterConfiguration.PelsWidth"
::= { win32PrinterConfigurationEntry 23 }

win32PrinterConfigurationPrintQuality OBJECT-TYPE
   SYNTAX         Uint32
   ACCESS         read-write
   STATUS         mandatory
   DESCRIPTION    "The PrintQuality property indicates the quality of the print job.<P>Example: Draft"
   REFERENCE      "Win32_PrinterConfiguration.PrintQuality"
::= { win32PrinterConfigurationEntry 24 }

win32PrinterConfigurationScale OBJECT-TYPE
   SYNTAX         Uint32
   ACCESS         read-write
   STATUS         mandatory
   DESCRIPTION    "The Scale property indicates the scale of the print job."
   REFERENCE      "Win32_PrinterConfiguration.Scale"
::= { win32PrinterConfigurationEntry 25 }

win32PrinterConfigurationSpecificationVersion OBJECT-TYPE
   SYNTAX         Uint32
   ACCESS         read-write
   STATUS         mandatory
   DESCRIPTION    "The SpecificationVersion property indicates the version of the specification."
   REFERENCE      "Win32_PrinterConfiguration.SpecificationVersion"
::= { win32PrinterConfigurationEntry 26 }

win32PrinterConfigurationTTOption OBJECT-TYPE
   SYNTAX         Uint32
   ACCESS         read-write
   STATUS         mandatory
   DESCRIPTION    ""
   REFERENCE      "Win32_PrinterConfiguration.TTOption"
::= { win32PrinterConfigurationEntry 27 }

win32PrinterConfigurationXResolution OBJECT-TYPE
   SYNTAX         Uint32
   ACCESS         read-write
   STATUS         mandatory
   DESCRIPTION    "The XResolution property indicates the resolution along the X axis (width) of the print job."
   REFERENCE      "Win32_PrinterConfiguration.XResolution"
::= { win32PrinterConfigurationEntry 28 }

win32PrinterConfigurationYResolution OBJECT-TYPE
   SYNTAX         Uint32
   ACCESS         read-write
   STATUS         mandatory
   DESCRIPTION    "The YResolution property indicates the resolution along the Y axis (height) of the print job."
   REFERENCE      "Win32_PrinterConfiguration.YResolution"
::= { win32PrinterConfigurationEntry 29 }

win32ProgramGroupTable OBJECT-TYPE
   SYNTAX         SEQUENCE OF Win32ProgramGroupEntry
   ACCESS         not-accessible
   STATUS         mandatory
   DESCRIPTION    "The Win32_ProgramGroup class represents a program group in a Win32 system, such as Accessories or Startup."
   REFERENCE      "Win32_ProgramGroup"
::= { win32WMI 550 }

win32ProgramGroupEntry OBJECT-TYPE
   SYNTAX         Win32ProgramGroupEntry
   ACCESS         not-accessible
   STATUS         mandatory
   DESCRIPTION    ""
   INDEX          { win32ProgramGroupKeyIndex }
::= { win32ProgramGroupTable 1 }

Win32ProgramGroupEntry ::= SEQUENCE
{
   win32ProgramGroupKeyIndex String,
   win32ProgramGroupGroupName String,
   win32ProgramGroupName String,
   win32ProgramGroupUserName String
}

win32ProgramGroupKeyIndex OBJECT-TYPE
   SYNTAX         String
   ACCESS         read-write
   STATUS         mandatory
   DESCRIPTION    ""
   REFERENCE      "Win32_ProgramGroup.KeyIndex"
::= { win32ProgramGroupEntry 1 }

win32ProgramGroupGroupName OBJECT-TYPE
   SYNTAX         String
   ACCESS         read-write
   STATUS         mandatory
   DESCRIPTION    "The GroupName property indicates the name of the Win32 program group.<P>Example: Accessories\\System Tools"
   REFERENCE      "Win32_ProgramGroup.GroupName"
::= { win32ProgramGroupEntry 2 }

win32ProgramGroupName OBJECT-TYPE
   SYNTAX         String
   ACCESS         read-write
   STATUS         mandatory
   DESCRIPTION    "The Name property indicates the user name followed by the group name.<P>Example: All Users:Accessories\\System Tools"
   REFERENCE      "Win32_ProgramGroup.Name"
::= { win32ProgramGroupEntry 3 }

win32ProgramGroupUserName OBJECT-TYPE
   SYNTAX         String
   ACCESS         read-write
   STATUS         mandatory
   DESCRIPTION    "The UserName property indicates the users who can access the Win32 program group.<P>Example: All Users"
   REFERENCE      "Win32_ProgramGroup.UserName"
::= { win32ProgramGroupEntry 4 }

win32SerialPortConfigurationTable OBJECT-TYPE
   SYNTAX         SEQUENCE OF Win32SerialPortConfigurationEntry
   ACCESS         not-accessible
   STATUS         mandatory
   DESCRIPTION    "The Win32_SerialPortConfiguration class represents a serial port configuration."
   REFERENCE      "Win32_SerialPortConfiguration"
::= { win32WMI 560 }

win32SerialPortConfigurationEntry OBJECT-TYPE
   SYNTAX         Win32SerialPortConfigurationEntry
   ACCESS         not-accessible
   STATUS         mandatory
   DESCRIPTION    ""
   INDEX          { win32SerialPortConfigurationKeyIndex }
::= { win32SerialPortConfigurationTable 1 }

Win32SerialPortConfigurationEntry ::= SEQUENCE
{
   win32SerialPortConfigurationKeyIndex String,
   win32SerialPortConfigurationAbortReadWriteOnError Boolean,
   win32SerialPortConfigurationBaudRate Uint32,
   win32SerialPortConfigurationBinaryModeEnabled Boolean,
   win32SerialPortConfigurationBitsPerByte Uint32,
   win32SerialPortConfigurationContinueXMitOnXOff Boolean,
   win32SerialPortConfigurationCTSOutflowControl Boolean,
   win32SerialPortConfigurationDiscardNULLBytes Boolean,
   win32SerialPortConfigurationDSROutflowControl Boolean,
   win32SerialPortConfigurationDSRSensitivity Boolean,
   win32SerialPortConfigurationDTRFlowControlType String,
   win32SerialPortConfigurationEOFCharacter Uint32,
   win32SerialPortConfigurationErrorReplaceCharacter Uint32,
   win32SerialPortConfigurationErrorReplacementEnabled Boolean,
   win32SerialPortConfigurationEventCharacter Uint32,
   win32SerialPortConfigurationIsBusy Boolean,
   win32SerialPortConfigurationName String,
   win32SerialPortConfigurationParity String,
   win32SerialPortConfigurationParityCheckEnabled Boolean,
   win32SerialPortConfigurationRTSFlowControlType String,
   win32SerialPortConfigurationStopBits String,
   win32SerialPortConfigurationXOffCharacter Uint32,
   win32SerialPortConfigurationXOffXMitThreshold Uint32,
   win32SerialPortConfigurationXOnCharacter Uint32,
   win32SerialPortConfigurationXOnXMitThreshold Uint32,
   win32SerialPortConfigurationXOnXOffInFlowControl Uint32,
   win32SerialPortConfigurationXOnXOffOutFlowControl Uint32
}

win32SerialPortConfigurationKeyIndex OBJECT-TYPE
   SYNTAX         String
   ACCESS         read-write
   STATUS         mandatory
   DESCRIPTION    ""
   REFERENCE      "Win32_SerialPortConfiguration.KeyIndex"
::= { win32SerialPortConfigurationEntry 1 }

win32SerialPortConfigurationAbortReadWriteOnError OBJECT-TYPE
   SYNTAX         Boolean
   ACCESS         read-write
   STATUS         mandatory
   DESCRIPTION    "The AbortReadWriteOnError property determines whether to abort a read or write operation when an error occurs.<P>Values: TRUE or FALSE. If TRUE, the operation is aborted."
   REFERENCE      "Win32_SerialPortConfiguration.AbortReadWriteOnError"
::= { win32SerialPortConfigurationEntry 2 }

win32SerialPortConfigurationBaudRate OBJECT-TYPE
   SYNTAX         Uint32
   ACCESS         read-write
   STATUS         mandatory
   DESCRIPTION    "The BaudRate property indicates the baud rate for this serial port.<P>Example: 9600"
   REFERENCE      "Win32_SerialPortConfiguration.BaudRate"
::= { win32SerialPortConfigurationEntry 3 }

win32SerialPortConfigurationBinaryModeEnabled OBJECT-TYPE
   SYNTAX         Boolean
   ACCESS         read-write
   STATUS         mandatory
   DESCRIPTION    "The BinaryModeEnabled property determines whether binary mode is enabled for the serial port.<P>Values: TRUE or FALSE. If TRUE, binary mode is enabled."
   REFERENCE      "Win32_SerialPortConfiguration.BinaryModeEnabled"
::= { win32SerialPortConfigurationEntry 4 }

win32SerialPortConfigurationBitsPerByte OBJECT-TYPE
   SYNTAX         Uint32
   ACCESS         read-write
   STATUS         mandatory
   DESCRIPTION    "The BitsPerByte property indicates the number of bits per byte for the Win32 serial port.<P>Example: 8"
   REFERENCE      "Win32_SerialPortConfiguration.BitsPerByte"
::= { win32SerialPortConfigurationEntry 5 }

win32SerialPortConfigurationContinueXMitOnXOff OBJECT-TYPE
   SYNTAX         Boolean
   ACCESS         read-write
   STATUS         mandatory
   DESCRIPTION    ""
   REFERENCE      "Win32_SerialPortConfiguration.ContinueXMitOnXOff"
::= { win32SerialPortConfigurationEntry 6 }

win32SerialPortConfigurationCTSOutflowControl OBJECT-TYPE
   SYNTAX         Boolean
   ACCESS         read-write
   STATUS         mandatory
   DESCRIPTION    "The CTSOutflowControl property determines whether data outflow control is enabled when there is a Clear To Send (CTS) condition.<P>Values: TRUE or FALSE. If TRUE, CTS outflow control is enabled."
   REFERENCE      "Win32_SerialPortConfiguration.CTSOutflowControl"
::= { win32SerialPortConfigurationEntry 7 }

win32SerialPortConfigurationDiscardNULLBytes OBJECT-TYPE
   SYNTAX         Boolean
   ACCESS         read-write
   STATUS         mandatory
   DESCRIPTION    "The DiscardNULLBytes property determines whether to discard NULL bytes (characters).<P>Values: TRUE or FALSE. If TRUE, NULL bytes are discarded."
   REFERENCE      "Win32_SerialPortConfiguration.DiscardNULLBytes"
::= { win32SerialPortConfigurationEntry 8 }

win32SerialPortConfigurationDSROutflowControl OBJECT-TYPE
   SYNTAX         Boolean
   ACCESS         read-write
   STATUS         mandatory
   DESCRIPTION    "The DSROutflowControl property determines whether data outflow control is enabled when there is a Data Set Read (DSR) condition.<P>Values: TRUE or FALSE. If TRUE, DSR outflow control is enabled."
   REFERENCE      "Win32_SerialPortConfiguration.DSROutflowControl"
::= { win32SerialPortConfigurationEntry 9 }

win32SerialPortConfigurationDSRSensitivity OBJECT-TYPE
   SYNTAX         Boolean
   ACCESS         read-write
   STATUS         mandatory
   DESCRIPTION    "The DSRSensitivity property determines whether DSR sensitivity is enabled.<P>Values: TRUE or FALSE. If TRUE, DSR sensitivity is enabled."
   REFERENCE      "Win32_SerialPortConfiguration.DSRSensitivity"
::= { win32SerialPortConfigurationEntry 10 }

win32SerialPortConfigurationDTRFlowControlType OBJECT-TYPE
   SYNTAX         String
   ACCESS         read-write
   STATUS         mandatory
   DESCRIPTION    "The DTRFlowControlType property indicates the type of data terminal ready (DTR) flow control.<P>Character Set: Alphanumeric"
   REFERENCE      "Win32_SerialPortConfiguration.DTRFlowControlType"
::= { win32SerialPortConfigurationEntry 11 }

win32SerialPortConfigurationEOFCharacter OBJECT-TYPE
   SYNTAX         Uint32
   ACCESS         read-write
   STATUS         mandatory
   DESCRIPTION    "The EOFCharacter property indicates the end of file (EOF) character.<P>Example: ^Z"
   REFERENCE      "Win32_SerialPortConfiguration.EOFCharacter"
::= { win32SerialPortConfigurationEntry 12 }

win32SerialPortConfigurationErrorReplaceCharacter OBJECT-TYPE
   SYNTAX         Uint32
   ACCESS         read-write
   STATUS         mandatory
   DESCRIPTION    "The ErrorReplaceCharacter property indicates the error replace character.<P>Example: ^C"
   REFERENCE      "Win32_SerialPortConfiguration.ErrorReplaceCharacter"
::= { win32SerialPortConfigurationEntry 13 }

win32SerialPortConfigurationErrorReplacementEnabled OBJECT-TYPE
   SYNTAX         Boolean
   ACCESS         read-write
   STATUS         mandatory
   DESCRIPTION    "The ErrorReplacementEnabled property determines whether error replacement is enabled.<P>Values: TRUE or FALSE. If TRUE, error replacement is enabled."
   REFERENCE      "Win32_SerialPortConfiguration.ErrorReplacementEnabled"
::= { win32SerialPortConfigurationEntry 14 }

win32SerialPortConfigurationEventCharacter OBJECT-TYPE
   SYNTAX         Uint32
   ACCESS         read-write
   STATUS         mandatory
   DESCRIPTION    "The EventCharacter property indicates the event character.<P>Example: ^e"
   REFERENCE      "Win32_SerialPortConfiguration.EventCharacter"
::= { win32SerialPortConfigurationEntry 15 }

win32SerialPortConfigurationIsBusy OBJECT-TYPE
   SYNTAX         Boolean
   ACCESS         read-write
   STATUS         mandatory
   DESCRIPTION    "The IsBusy property determines whether the serial port is busy.<P>Values: TRUE or FALSE. If TRUE, the serial port is busy."
   REFERENCE      "Win32_SerialPortConfiguration.IsBusy"
::= { win32SerialPortConfigurationEntry 16 }

win32SerialPortConfigurationName OBJECT-TYPE
   SYNTAX         String
   ACCESS         read-write
   STATUS         mandatory
   DESCRIPTION    "The Name property indicates the name of the Win32 serial port.<P>Example: COM1"
   REFERENCE      "Win32_SerialPortConfiguration.Name"
::= { win32SerialPortConfigurationEntry 17 }

win32SerialPortConfigurationParity OBJECT-TYPE
   SYNTAX         String
   ACCESS         read-write
   STATUS         mandatory
   DESCRIPTION    "The Parity property indicates the type of parity used.<P>Example: None, Even, or Odd"
   REFERENCE      "Win32_SerialPortConfiguration.Parity"
::= { win32SerialPortConfigurationEntry 18 }

win32SerialPortConfigurationParityCheckEnabled OBJECT-TYPE
   SYNTAX         Boolean
   ACCESS         read-write
   STATUS         mandatory
   DESCRIPTION    "The ParityCheckEnabled property determines whether parity checking is enabled.<P>Values: TRUE or FALSE. If TRUE, parity checking is enabled."
   REFERENCE      "Win32_SerialPortConfiguration.ParityCheckEnabled"
::= { win32SerialPortConfigurationEntry 19 }

win32SerialPortConfigurationRTSFlowControlType OBJECT-TYPE
   SYNTAX         String
   ACCESS         read-write
   STATUS         mandatory
   DESCRIPTION    "The RTSFlowControlType property indicates the type of ready to send (RTS) flow control.<P>Character Set: Alphanumeric"
   REFERENCE      "Win32_SerialPortConfiguration.RTSFlowControlType"
::= { win32SerialPortConfigurationEntry 20 }

win32SerialPortConfigurationStopBits OBJECT-TYPE
   SYNTAX         String
   ACCESS         read-write
   STATUS         mandatory
   DESCRIPTION    "The StopBits property indicates the number of stop bits for the Win32 serial port.<P>Example: 1"
   REFERENCE      "Win32_SerialPortConfiguration.StopBits"
::= { win32SerialPortConfigurationEntry 21 }

win32SerialPortConfigurationXOffCharacter OBJECT-TYPE
   SYNTAX         Uint32
   ACCESS         read-write
   STATUS         mandatory
   DESCRIPTION    "The XOffCharacter property indicates the XOff character for the Win32 serial port."
   REFERENCE      "Win32_SerialPortConfiguration.XOffCharacter"
::= { win32SerialPortConfigurationEntry 22 }

win32SerialPortConfigurationXOffXMitThreshold OBJECT-TYPE
   SYNTAX         Uint32
   ACCESS         read-write
   STATUS         mandatory
   DESCRIPTION    "The XOffXMitThreshold property indicates the XOff transmit threshold for the Win32 serial port."
   REFERENCE      "Win32_SerialPortConfiguration.XOffXMitThreshold"
::= { win32SerialPortConfigurationEntry 23 }

win32SerialPortConfigurationXOnCharacter OBJECT-TYPE
   SYNTAX         Uint32
   ACCESS         read-write
   STATUS         mandatory
   DESCRIPTION    "The XOnCharacter property indicates the XOn character."
   REFERENCE      "Win32_SerialPortConfiguration.XOnCharacter"
::= { win32SerialPortConfigurationEntry 24 }

win32SerialPortConfigurationXOnXMitThreshold OBJECT-TYPE
   SYNTAX         Uint32
   ACCESS         read-write
   STATUS         mandatory
   DESCRIPTION    "The XOnXMitThreshold property indicates the XOn transmit threshold."
   REFERENCE      "Win32_SerialPortConfiguration.XOnXMitThreshold"
::= { win32SerialPortConfigurationEntry 25 }

win32SerialPortConfigurationXOnXOffInFlowControl OBJECT-TYPE
   SYNTAX         Uint32
   ACCESS         read-write
   STATUS         mandatory
   DESCRIPTION    "The XOnXOffInFlowControl property indicates the amount of data inflow."
   REFERENCE      "Win32_SerialPortConfiguration.XOnXOffInFlowControl"
::= { win32SerialPortConfigurationEntry 26 }

win32SerialPortConfigurationXOnXOffOutFlowControl OBJECT-TYPE
   SYNTAX         Uint32
   ACCESS         read-write
   STATUS         mandatory
   DESCRIPTION    "The XOnXOffOutFlowControl property indicates the amount of data outflow."
   REFERENCE      "Win32_SerialPortConfiguration.XOnXOffOutFlowControl"
::= { win32SerialPortConfigurationEntry 27 }

win32TimeZoneTable OBJECT-TYPE
   SYNTAX         SEQUENCE OF Win32TimeZoneEntry
   ACCESS         not-accessible
   STATUS         mandatory
   DESCRIPTION    "The Win32_TimeZone class represents the time zone information for a Win32 system. For example, (GMT08:00) Pacific Time (US & Canada); Tijuana."
   REFERENCE      "Win32_TimeZone"
::= { win32WMI 570 }

win32TimeZoneEntry OBJECT-TYPE
   SYNTAX         Win32TimeZoneEntry
   ACCESS         not-accessible
   STATUS         mandatory
   DESCRIPTION    ""
   INDEX          { win32TimeZoneKeyIndex }
::= { win32TimeZoneTable 1 }

Win32TimeZoneEntry ::= SEQUENCE
{
   win32TimeZoneKeyIndex String,
   win32TimeZoneBias Sint32,
   win32TimeZoneDaylightBias Sint32,
   win32TimeZoneDaylightDay Uint32,
   win32TimeZoneDaylightDayOfWeek Uint8,
   win32TimeZoneDaylightHour Uint32,
   win32TimeZoneDaylightMillisecond Uint32,
   win32TimeZoneDaylightMinute Uint32,
   win32TimeZoneDaylightMonth Uint32,
   win32TimeZoneDaylightName String,
   win32TimeZoneDaylightSecond Uint32,
   win32TimeZoneDaylightYear Uint32,
   win32TimeZoneStandardBias Uint32,
   win32TimeZoneStandardDay Uint32,
   win32TimeZoneStandardDayOfWeek Uint8,
   win32TimeZoneStandardHour Uint32,
   win32TimeZoneStandardMillisecond Uint32,
   win32TimeZoneStandardMinute Uint32,
   win32TimeZoneStandardMonth Uint32,
   win32TimeZoneStandardName String,
   win32TimeZoneStandardSecond Uint32,
   win32TimeZoneStandardYear Uint32
}

win32TimeZoneKeyIndex OBJECT-TYPE
   SYNTAX         String
   ACCESS         read-write
   STATUS         mandatory
   DESCRIPTION    ""
   REFERENCE      "Win32_TimeZone.KeyIndex"
::= { win32TimeZoneEntry 1 }

win32TimeZoneBias OBJECT-TYPE
   SYNTAX         Sint32
   ACCESS         read-write
   STATUS         mandatory
   DESCRIPTION    "The bias property indicates the bias of the time zone."
   REFERENCE      "Win32_TimeZone.Bias"
::= { win32TimeZoneEntry 2 }

win32TimeZoneDaylightBias OBJECT-TYPE
   SYNTAX         Sint32
   ACCESS         read-write
   STATUS         mandatory
   DESCRIPTION    "The DaylightBias property indicates the bias during daylight saving time."
   REFERENCE      "Win32_TimeZone.DaylightBias"
::= { win32TimeZoneEntry 3 }

win32TimeZoneDaylightDay OBJECT-TYPE
   SYNTAX         Uint32
   ACCESS         read-write
   STATUS         mandatory
   DESCRIPTION    "The DaylightDay property indicates the day during daylight saving time.<P>Example: 31"
   REFERENCE      "Win32_TimeZone.DaylightDay"
::= { win32TimeZoneEntry 4 }

win32TimeZoneDaylightDayOfWeek OBJECT-TYPE
   SYNTAX         Uint8
   ACCESS         read-write
   STATUS         mandatory
   DESCRIPTION    "The DaylightDayOfWeek property indicates the day of the week during daylight saving time.<P>Example: Monday"
   REFERENCE      "Win32_TimeZone.DaylightDayOfWeek"
::= { win32TimeZoneEntry 5 }

win32TimeZoneDaylightHour OBJECT-TYPE
   SYNTAX         Uint32
   ACCESS         read-write
   STATUS         mandatory
   DESCRIPTION    "The DaylightHour property indicates the hour of the day during daylight saving time.<P>Example: 11"
   REFERENCE      "Win32_TimeZone.DaylightHour"
::= { win32TimeZoneEntry 6 }

win32TimeZoneDaylightMillisecond OBJECT-TYPE
   SYNTAX         Uint32
   ACCESS         read-write
   STATUS         mandatory
   DESCRIPTION    "The DaylightMillisecond property indicates a millionth of a second during daylight saving time."
   REFERENCE      "Win32_TimeZone.DaylightMillisecond"
::= { win32TimeZoneEntry 7 }

win32TimeZoneDaylightMinute OBJECT-TYPE
   SYNTAX         Uint32
   ACCESS         read-write
   STATUS         mandatory
   DESCRIPTION    "The DaylightMinute property indicates a minute during daylight saving time.<P>Example: 59"
   REFERENCE      "Win32_TimeZone.DaylightMinute"
::= { win32TimeZoneEntry 8 }

win32TimeZoneDaylightMonth OBJECT-TYPE
   SYNTAX         Uint32
   ACCESS         read-write
   STATUS         mandatory
   DESCRIPTION    "The DaylightMonth property indicates the month of the year during daylight saving time.<P>Example: 4"
   REFERENCE      "Win32_TimeZone.DaylightMonth"
::= { win32TimeZoneEntry 9 }

win32TimeZoneDaylightName OBJECT-TYPE
   SYNTAX         String
   ACCESS         read-write
   STATUS         mandatory
   DESCRIPTION    "The DaylightName property indicates the name during daylight saving time.<P>Character Set: Alphanumeric"
   REFERENCE      "Win32_TimeZone.DaylightName"
::= { win32TimeZoneEntry 10 }

win32TimeZoneDaylightSecond OBJECT-TYPE
   SYNTAX         Uint32
   ACCESS         read-write
   STATUS         mandatory
   DESCRIPTION    "The DaylightSecond property indicates a second during daylight saving time.<P>Example: 59"
   REFERENCE      "Win32_TimeZone.DaylightSecond"
::= { win32TimeZoneEntry 11 }

win32TimeZoneDaylightYear OBJECT-TYPE
   SYNTAX         Uint32
   ACCESS         read-write
   STATUS         mandatory
   DESCRIPTION    "The DaylightYear property indicates the year during daylight saving time.<P>Example: 97"
   REFERENCE      "Win32_TimeZone.DaylightYear"
::= { win32TimeZoneEntry 12 }

win32TimeZoneStandardBias OBJECT-TYPE
   SYNTAX         Uint32
   ACCESS         read-write
   STATUS         mandatory
   DESCRIPTION    "The StandardBias property indicates the bias during standard time."
   REFERENCE      "Win32_TimeZone.StandardBias"
::= { win32TimeZoneEntry 13 }

win32TimeZoneStandardDay OBJECT-TYPE
   SYNTAX         Uint32
   ACCESS         read-write
   STATUS         mandatory
   DESCRIPTION    "The StandardDay property indicates the day during standard time.<P>Example: 31"
   REFERENCE      "Win32_TimeZone.StandardDay"
::= { win32TimeZoneEntry 14 }

win32TimeZoneStandardDayOfWeek OBJECT-TYPE
   SYNTAX         Uint8
   ACCESS         read-write
   STATUS         mandatory
   DESCRIPTION    "The StandardDayOfWeek property indicates the day of the week during standard time.<P>Example: Monday"
   REFERENCE      "Win32_TimeZone.StandardDayOfWeek"
::= { win32TimeZoneEntry 15 }

win32TimeZoneStandardHour OBJECT-TYPE
   SYNTAX         Uint32
   ACCESS         read-write
   STATUS         mandatory
   DESCRIPTION    "The StandardHour property indicates the hour of the day during standard time.<P>Example: 11"
   REFERENCE      "Win32_TimeZone.StandardHour"
::= { win32TimeZoneEntry 16 }

win32TimeZoneStandardMillisecond OBJECT-TYPE
   SYNTAX         Uint32
   ACCESS         read-write
   STATUS         mandatory
   DESCRIPTION    "The StandardMillisecond property indicates a millionth of a second during standard time."
   REFERENCE      "Win32_TimeZone.StandardMillisecond"
::= { win32TimeZoneEntry 17 }

win32TimeZoneStandardMinute OBJECT-TYPE
   SYNTAX         Uint32
   ACCESS         read-write
   STATUS         mandatory
   DESCRIPTION    "The StandardMinute property indicates a minute during standard time.<P>Example: 59"
   REFERENCE      "Win32_TimeZone.StandardMinute"
::= { win32TimeZoneEntry 18 }

win32TimeZoneStandardMonth OBJECT-TYPE
   SYNTAX         Uint32
   ACCESS         read-write
   STATUS         mandatory
   DESCRIPTION    "The StandardMonth property indicates the month of the year during standard time.<P>Example: 12"
   REFERENCE      "Win32_TimeZone.StandardMonth"
::= { win32TimeZoneEntry 19 }

win32TimeZoneStandardName OBJECT-TYPE
   SYNTAX         String
   ACCESS         read-write
   STATUS         mandatory
   DESCRIPTION    "The StandardName property indicates the name during standard time.<P>Character Set: Alphanumeric"
   REFERENCE      "Win32_TimeZone.StandardName"
::= { win32TimeZoneEntry 20 }

win32TimeZoneStandardSecond OBJECT-TYPE
   SYNTAX         Uint32
   ACCESS         read-write
   STATUS         mandatory
   DESCRIPTION    "The StandardSecond property indicates a second during standard time.<P>Example: 59"
   REFERENCE      "Win32_TimeZone.StandardSecond"
::= { win32TimeZoneEntry 21 }

win32TimeZoneStandardYear OBJECT-TYPE
   SYNTAX         Uint32
   ACCESS         read-write
   STATUS         mandatory
   DESCRIPTION    "The StandardYear property indicates the year during standard time.<P>Example: 97"
   REFERENCE      "Win32_TimeZone.StandardYear"
::= { win32TimeZoneEntry 22 }

win32VideoConfigurationTable OBJECT-TYPE
   SYNTAX         SEQUENCE OF Win32VideoConfigurationEntry
   ACCESS         not-accessible
   STATUS         mandatory
   DESCRIPTION    "The Win32_VideoConfiguration class represents a configuration of a video subsystem."
   REFERENCE      "Win32_VideoConfiguration"
::= { win32WMI 580 }

win32VideoConfigurationEntry OBJECT-TYPE
   SYNTAX         Win32VideoConfigurationEntry
   ACCESS         not-accessible
   STATUS         mandatory
   DESCRIPTION    ""
   INDEX          { win32VideoConfigurationKeyIndex }
::= { win32VideoConfigurationTable 1 }

Win32VideoConfigurationEntry ::= SEQUENCE
{
   win32VideoConfigurationKeyIndex String,
   win32VideoConfigurationActualColorResolution Uint32,
   win32VideoConfigurationAdapterChipType String,
   win32VideoConfigurationAdapterCompatibility String,
   win32VideoConfigurationAdapterDACType String,
   win32VideoConfigurationAdapterDescription String,
   win32VideoConfigurationAdapterRAM Uint32,
   win32VideoConfigurationAdapterType String,
   win32VideoConfigurationBitsPerPixel Uint32,
   win32VideoConfigurationColorPlanes Uint32,
   win32VideoConfigurationColorTableEntries Uint32,
   win32VideoConfigurationDeviceSpecificPens Uint32,
   win32VideoConfigurationDriverDate Datetime,
   win32VideoConfigurationHorizontalResolution Uint32,
   win32VideoConfigurationInfFilename String,
   win32VideoConfigurationInfSection String,
   win32VideoConfigurationInstalledDisplayDrivers String,
   win32VideoConfigurationMonitorManufacturer String,
   win32VideoConfigurationMonitorType String,
   win32VideoConfigurationName String,
   win32VideoConfigurationPixelsPerXLogicalInch Uint32,
   win32VideoConfigurationPixelsPerYLogicalInch Uint32,   
   win32VideoConfigurationRefreshRate Uint32,
   win32VideoConfigurationScanMode String,
   win32VideoConfigurationScreenHeight Uint32,
   win32VideoConfigurationScreenWidth Uint32,
   win32VideoConfigurationSystemPaletteEntries Uint32,
   win32VideoConfigurationVerticalResolution Uint32
}

win32VideoConfigurationKeyIndex OBJECT-TYPE
   SYNTAX         String
   ACCESS         read-write
   STATUS         mandatory
   DESCRIPTION    ""
   REFERENCE      "Win32_VideoConfiguration.KeyIndex"
::= { win32VideoConfigurationEntry 1 }

win32VideoConfigurationActualColorResolution OBJECT-TYPE
   SYNTAX         Uint32
   ACCESS         read-write
   STATUS         mandatory
   DESCRIPTION    "The ActualColorResolution property indicates the actual color resolution of the video display.<P>Example: 256"
   REFERENCE      "Win32_VideoConfiguration.ActualColorResolution"
::= { win32VideoConfigurationEntry 2 }

win32VideoConfigurationAdapterChipType OBJECT-TYPE
   SYNTAX         String
   ACCESS         read-write
   STATUS         mandatory
   DESCRIPTION    "The AdapterChipType property indicates the name of the adapter chip.<P>Example: s3"
   REFERENCE      "Win32_VideoConfiguration.AdapterChipType"
::= { win32VideoConfigurationEntry 3 }

win32VideoConfigurationAdapterCompatibility OBJECT-TYPE
   SYNTAX         String
   ACCESS         read-write
   STATUS         mandatory
   DESCRIPTION    ""
   REFERENCE      "Win32_VideoConfiguration.AdapterCompatibility"
::= { win32VideoConfigurationEntry 4 }

win32VideoConfigurationAdapterDACType OBJECT-TYPE
   SYNTAX         String
   ACCESS         read-write
   STATUS         mandatory
   DESCRIPTION    "The AdapterDACType property indicates the DAC type of the adapter.<P>Character Set: Alphanumeric"
   REFERENCE      "Win32_VideoConfiguration.AdapterDACType"
::= { win32VideoConfigurationEntry 5 }

win32VideoConfigurationAdapterDescription OBJECT-TYPE
   SYNTAX         String
   ACCESS         read-write
   STATUS         mandatory
   DESCRIPTION    "The AdapterDescription property indicates the descriptive name of the video adapter.<P>Character Set: Alphanumeric"
   REFERENCE      "Win32_VideoConfiguration.AdapterDescription"
::= { win32VideoConfigurationEntry 6 }

win32VideoConfigurationAdapterRAM OBJECT-TYPE
   SYNTAX         Uint32
   ACCESS         read-write
   STATUS         mandatory
   DESCRIPTION    "The AdapterRAM property indicates the memory size (in bytes) of the video adapter.<P>Example: 64000"
   REFERENCE      "Win32_VideoConfiguration.AdapterRAM"
::= { win32VideoConfigurationEntry 7 }

win32VideoConfigurationAdapterType OBJECT-TYPE
   SYNTAX         String
   ACCESS         read-write
   STATUS         mandatory
   DESCRIPTION    "The AdapterType property indicates the type of video adapter.<P>Character Set: Alphanumeric"
   REFERENCE      "Win32_VideoConfiguration.AdapterType"
::= { win32VideoConfigurationEntry 8 }

win32VideoConfigurationBitsPerPixel OBJECT-TYPE
   SYNTAX         Uint32
   ACCESS         read-write
   STATUS         mandatory
   DESCRIPTION    "The BitsPerPixel property indicates the number of bits per pixel.<P>Example: 8"
   REFERENCE      "Win32_VideoConfiguration.BitsPerPixel"
::= { win32VideoConfigurationEntry 9 }

win32VideoConfigurationColorPlanes OBJECT-TYPE
   SYNTAX         Uint32
   ACCESS         read-write
   STATUS         mandatory
   DESCRIPTION    "The ColorPlanes property indicates the number of color planes.<P>Example: 4"
   REFERENCE      "Win32_VideoConfiguration.ColorPlanes"
::= { win32VideoConfigurationEntry 10 }

win32VideoConfigurationColorTableEntries OBJECT-TYPE
   SYNTAX         Uint32
   ACCESS         read-write
   STATUS         mandatory
   DESCRIPTION    "The ColorTableEntries property indicates the number of color table entries.<P>Example: 256"
   REFERENCE      "Win32_VideoConfiguration.ColorTableEntries"
::= { win32VideoConfigurationEntry 11 }

win32VideoConfigurationDeviceSpecificPens OBJECT-TYPE
   SYNTAX         Uint32
   ACCESS         read-write
   STATUS         mandatory
   DESCRIPTION    "The DeviceSpecificPens property indicates the number of pens.<P>Example: 3"
   REFERENCE      "Win32_VideoConfiguration.DeviceSpecificPens"
::= { win32VideoConfigurationEntry 12 }

win32VideoConfigurationDriverDate OBJECT-TYPE
   SYNTAX         Datetime
   ACCESS         read-write
   STATUS         mandatory
   DESCRIPTION    "The DriverDate property indicates the date and time of the currently-installed video driver."
   REFERENCE      "Win32_VideoConfiguration.DriverDate"
::= { win32VideoConfigurationEntry 13 }

win32VideoConfigurationHorizontalResolution OBJECT-TYPE
   SYNTAX         Uint32
   ACCESS         read-write
   STATUS         mandatory
   DESCRIPTION    "The HorizontalResolution property indicates the horizontal resolution of the display."
   REFERENCE      "Win32_VideoConfiguration.HorizontalResolution"
::= { win32VideoConfigurationEntry 14 }

win32VideoConfigurationInfFilename OBJECT-TYPE
   SYNTAX         String
   ACCESS         read-write
   STATUS         mandatory
   DESCRIPTION    "The InfFilename property indicates the path to the INF file.<P>Example: C:\\WINNT\\SYSTEM32\\DRIVERS"
   REFERENCE      "Win32_VideoConfiguration.InfFilename"
::= { win32VideoConfigurationEntry 15 }

win32VideoConfigurationInfSection OBJECT-TYPE
   SYNTAX         String
   ACCESS         read-write
   STATUS         mandatory
   DESCRIPTION    "The InfSection property indicates the section of the INF file where the Win32 video configuration information resides.<P>Character Set: Alphanumeric"
   REFERENCE      "Win32_VideoConfiguration.InfSection"
::= { win32VideoConfigurationEntry 16 }

win32VideoConfigurationInstalledDisplayDrivers OBJECT-TYPE
   SYNTAX         String
   ACCESS         read-write
   STATUS         mandatory
   DESCRIPTION    "The InstalledDisplayDriver property indicates the name of the installed display driver.<P>Character Set: Alphanumeric"
   REFERENCE      "Win32_VideoConfiguration.InstalledDisplayDrivers"
::= { win32VideoConfigurationEntry 17 }

win32VideoConfigurationMonitorManufacturer OBJECT-TYPE
   SYNTAX         String
   ACCESS         read-write
   STATUS         mandatory
   DESCRIPTION    "The MonitorManufacturer property indicates the manufacturer of the video adapter.<P>Example: NEC"
   REFERENCE      "Win32_VideoConfiguration.MonitorManufacturer"
::= { win32VideoConfigurationEntry 18 }

win32VideoConfigurationMonitorType OBJECT-TYPE
   SYNTAX         String
   ACCESS         read-write
   STATUS         mandatory
   DESCRIPTION    "The MonitorType property indicates the type of monitor.<P>Example: NEC 5FGp"
   REFERENCE      "Win32_VideoConfiguration.MonitorType"
::= { win32VideoConfigurationEntry 19 }

win32VideoConfigurationName OBJECT-TYPE
   SYNTAX         String
   ACCESS         read-write
   STATUS         mandatory
   DESCRIPTION    "The Name property indicates the name of the video adapter.<P>Character Set: Alphanumeric"
   REFERENCE      "Win32_VideoConfiguration.Name"
::= { win32VideoConfigurationEntry 20 }

win32VideoConfigurationPixelsPerXLogicalInch OBJECT-TYPE
   SYNTAX         Uint32
   ACCESS         read-write
   STATUS         mandatory
   DESCRIPTION    "The PixelsPerXLogicalInch property indicates the number of pixels per logical inch along the X axis (horizontal direction) of the display."
   REFERENCE      "Win32_VideoConfiguration.PixelsPerXLogicalInch"
::= { win32VideoConfigurationEntry 21 }

win32VideoConfigurationPixelsPerYLogicalInch OBJECT-TYPE
   SYNTAX         Uint32
   ACCESS         read-write
   STATUS         mandatory
   DESCRIPTION    "The PixelsPerYLogicalInch property indicates the number of pixels per logical inch along the Y axis (vertical direction) of the display."
   REFERENCE      "Win32_VideoConfiguration.PixelsPerYLogicalInch"
::= { win32VideoConfigurationEntry 22 }

win32VideoConfigurationRefreshRate OBJECT-TYPE
   SYNTAX         Uint32
   ACCESS         read-write
   STATUS         mandatory
   DESCRIPTION    "The RefreshRate property indicates the refresh rate of the video configuration.  A value of 0 or 1 indicates a default rate is being used."
   REFERENCE      "Win32_VideoConfiguration.RefreshRate"
::= { win32VideoConfigurationEntry 23 }

win32VideoConfigurationScanMode OBJECT-TYPE
   SYNTAX         String
   ACCESS         read-write
   STATUS         mandatory
   DESCRIPTION    "The ScanMode property indicates the scan mode of the video adapter.<P>Character Set: Alphanumeric"
   REFERENCE      "Win32_VideoConfiguration.ScanMode"
::= { win32VideoConfigurationEntry 24 }

win32VideoConfigurationScreenHeight OBJECT-TYPE
   SYNTAX         Uint32
   ACCESS         read-write
   STATUS         mandatory
   DESCRIPTION    "The ScreenHeight property indicates the height of the display screen."
   REFERENCE      "Win32_VideoConfiguration.ScreenHeight"
::= { win32VideoConfigurationEntry 25 }

win32VideoConfigurationScreenWidth OBJECT-TYPE
   SYNTAX         Uint32
   ACCESS         read-write
   STATUS         mandatory
   DESCRIPTION    "The ScreenWidth property indicates the width of the display screen."
   REFERENCE      "Win32_VideoConfiguration.ScreenWidth"
::= { win32VideoConfigurationEntry 26 }

win32VideoConfigurationSystemPaletteEntries OBJECT-TYPE
   SYNTAX         Uint32
   ACCESS         read-write
   STATUS         mandatory
   DESCRIPTION    "The SystemPaletteEntries property indicates the number of system palette entries.<P>Example: 256"
   REFERENCE      "Win32_VideoConfiguration.SystemPaletteEntries"
::= { win32VideoConfigurationEntry 27 }

win32VideoConfigurationVerticalResolution OBJECT-TYPE
   SYNTAX         Uint32
   ACCESS         read-write
   STATUS         mandatory
   DESCRIPTION    "The VerticalResolution property indicates the vertical resolution of the display."
   REFERENCE      "Win32_VideoConfiguration.VerticalResolution"
::= { win32VideoConfigurationEntry 28 }

win32LogicalDiskToPartitionTable OBJECT-TYPE
   SYNTAX         SEQUENCE OF Win32LogicalDiskToPartitionEntry
   ACCESS         not-accessible
   STATUS         mandatory
   DESCRIPTION    "The Win32_LogicalDiskToPartition class represents an association between a logical disk drive and the disk partition it resides on."
   REFERENCE      "Win32_LogicalDiskToPartition"
::= { win32WMI 590 }

win32LogicalDiskToPartitionEntry OBJECT-TYPE
   SYNTAX         Win32LogicalDiskToPartitionEntry
   ACCESS         not-accessible
   STATUS         mandatory
   DESCRIPTION    ""
   INDEX          { win32LogicalDiskToPartitionKeyIndex }
::= { win32LogicalDiskToPartitionTable 1 }

Win32LogicalDiskToPartitionEntry ::= SEQUENCE
{
   win32LogicalDiskToPartitionKeyIndex String,
   win32LogicalDiskToPartitionAntecedent String,
   win32LogicalDiskToPartitionDependent String
}

win32LogicalDiskToPartitionKeyIndex OBJECT-TYPE
   SYNTAX         String
   ACCESS         read-write
   STATUS         mandatory
   DESCRIPTION    ""
   REFERENCE      "Win32_LogicalDiskToPartition.KeyIndex"
::= { win32LogicalDiskToPartitionEntry 1 }

win32LogicalDiskToPartitionAntecedent OBJECT-TYPE
   SYNTAX         String
   ACCESS         read-write
   STATUS         mandatory
   DESCRIPTION    "The Antecedent reference represents the Win32_DiskPartition containing the properties of a disk partition where the logical disk resides."
   REFERENCE      "Win32_LogicalDiskToPartition.Antecedent"
::= { win32LogicalDiskToPartitionEntry 2 }

win32LogicalDiskToPartitionDependent OBJECT-TYPE
   SYNTAX         String
   ACCESS         read-write
   STATUS         mandatory
   DESCRIPTION    "The Dependent reference represents the Win32_LogicalDisk containing the properties of a logical disk that resides on a physical disk partition."
   REFERENCE      "Win32_LogicalDiskToPartition.Dependent"
::= { win32LogicalDiskToPartitionEntry 3 }

win32DiskDriveToDiskPartitionTable OBJECT-TYPE
   SYNTAX         SEQUENCE OF Win32DiskDriveToDiskPartitionEntry
   ACCESS         not-accessible
   STATUS         mandatory
   DESCRIPTION    "The Win32_DiskDriveToDiskPartition class represents an association between a disk drive and a partition existing on it."
   REFERENCE      "Win32_DiskDriveToDiskPartition"
::= { win32WMI 600 }

win32DiskDriveToDiskPartitionEntry OBJECT-TYPE
   SYNTAX         Win32DiskDriveToDiskPartitionEntry
   ACCESS         not-accessible
   STATUS         mandatory
   DESCRIPTION    ""
   INDEX          { win32DiskDriveToDiskPartitionKeyIndex }
::= { win32DiskDriveToDiskPartitionTable 1 }

Win32DiskDriveToDiskPartitionEntry ::= SEQUENCE
{
   win32DiskDriveToDiskPartitionKeyIndex String,
   win32DiskDriveToDiskPartitionAntecedent String,
   win32DiskDriveToDiskPartitionDependent String
}

win32DiskDriveToDiskPartitionKeyIndex OBJECT-TYPE
   SYNTAX         String
   ACCESS         read-write
   STATUS         mandatory
   DESCRIPTION    ""
   REFERENCE      "Win32_DiskDriveToDiskPartition.KeyIndex"
::= { win32DiskDriveToDiskPartitionEntry 1 }

win32DiskDriveToDiskPartitionAntecedent OBJECT-TYPE
   SYNTAX         String
   ACCESS         read-write
   STATUS         mandatory
   DESCRIPTION    "The Antecedent reference represents the Win32_DiskDrive containing the properties of the disk drive where the partition exists."
   REFERENCE      "Win32_DiskDriveToDiskPartition.Antecedent"
::= { win32DiskDriveToDiskPartitionEntry 2 }

win32DiskDriveToDiskPartitionDependent OBJECT-TYPE
   SYNTAX         String
   ACCESS         read-write
   STATUS         mandatory
   DESCRIPTION    "The Dependent reference represents the Win32_DiskPartition containing the properties of a disk partition residing on the disk drive."
   REFERENCE      "Win32_DiskDriveToDiskPartition.Dependent"
::= { win32DiskDriveToDiskPartitionEntry 3 }


cimBIOSElementTable OBJECT-TYPE
   SYNTAX         SEQUENCE OF cimBIOSElementEntry
   ACCESS         not-accessible
   STATUS         mandatory
   DESCRIPTION    ""
   REFERENCE      "CIM_BIOSElement"
::= { win32WMI 610 }

cimBIOSElementEntry OBJECT-TYPE
   SYNTAX         cimBIOSElementEntry
   ACCESS         not-accessible
   STATUS         mandatory
   DESCRIPTION    ""
   INDEX          { cimBIOSElementKeyIndex }
::= { cimBIOSElementTable 1 }

cimBIOSElementEntry ::= SEQUENCE
{
   cimBIOSElementKeyIndex String,
   cimBIOSElementName String,
   cimBIOSElementManufacturer String,
   cimBIOSElementDescription String,
   cimBIOSElementVersion String,
   cimBIOSElementBuildNumber String,
   cimBIOSElementReleaseDate Datetime
}

cimBIOSElementKeyIndex OBJECT-TYPE
   SYNTAX         String
   ACCESS         read-write
   STATUS         mandatory
   DESCRIPTION    ""
   REFERENCE      "CIM_BIOSElement.KeyIndex"
::= { cimBIOSElementEntry 1 }

cimBIOSElementName OBJECT-TYPE
   SYNTAX         String
   ACCESS         read-write
   STATUS         mandatory
   DESCRIPTION    ""
   REFERENCE      "CIM_BIOSElement.Name"
::= { cimBIOSElementEntry 2 }

cimBIOSElementManufacturer OBJECT-TYPE
   SYNTAX         String
   ACCESS         read-write
   STATUS         mandatory
   DESCRIPTION    ""
   REFERENCE      "CIM_BIOSElement.Manufacturer"
::= { cimBIOSElementEntry 3 }

cimBIOSElementDescription OBJECT-TYPE
   SYNTAX         String
   ACCESS         read-write
   STATUS         mandatory
   DESCRIPTION    ""
   REFERENCE      "CIM_BIOSElement.Description"
::= { cimBIOSElementEntry 4 }

cimBIOSElementVersion OBJECT-TYPE
   SYNTAX         String
   ACCESS         read-write
   STATUS         mandatory
   DESCRIPTION    ""
   REFERENCE      "CIM_BIOSElement.Version"
::= { cimBIOSElementEntry 5 }

cimBIOSElementBuildNumber OBJECT-TYPE
   SYNTAX         String
   ACCESS         read-write
   STATUS         mandatory
   DESCRIPTION    ""
   REFERENCE      "CIM_BIOSElement.BuildNumber"
::= { cimBIOSElementEntry 6 }

cimBIOSElementReleaseDate OBJECT-TYPE
   SYNTAX         Datetime
   ACCESS         read-write
   STATUS         mandatory
   DESCRIPTION    ""
   REFERENCE      "CIM_BIOSElement.ReleaseDate"
::= { cimBIOSElementEntry 7 }

END
