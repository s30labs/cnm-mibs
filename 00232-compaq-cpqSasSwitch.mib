-- ****************************************************************************
-- :CPQ,DEV:
--
-- * SAS SWITCH SNMP MIB DEFINITIONS
--
-- * $Date: 2008/11/01 11:32:58Z $
-- * $Revision: 1.00 $
--
-- Hewlett-Packard Company
-- Confidential - Need To Know
-- ****************************************************************************
-- :CPQ,ENDDEV:
--
--                                  SAS Switch
--           Management Information Base for SNMP Network Management
--
--
--      Copyright 1992,2009 Hewlett-Packard Development Company, L.P.
--      Hewlett-Packard Company shall not be liable for technical or
--      editorial errors or omissions contained herein. The information in
--      this document is provided "as is" without warranty of any kind and
--      is subject to change without notice. The warranties for HP products
--      are set forth in the express limited warranty statements
--      accompanying such products. Nothing herein should be construed as
--      constituting an additional warranty.
--
--      Confidential computer software. Valid license from HP required for
--      possession, use or copying. Consistent with FAR 12.211 and 12.212,
--      Commercial Computer Software, Computer Software Documentation, and
--      Technical Data for Commercial Items are licensed to the U.S.
--      Government under vendor's standard commercial license.
--
--      Refer to the READMIB.RDM file for more information about the
--      organization of the information in the Compaq Enterprise.
--
--      The Compaq Enterprise number is 232.
--      The ASN.1 prefix to, and including the Compaq Enterprise is:
--           1.3.6.1.4.1.232
--
-- ****************************************************************************

CPQSASSWITCH-MIB DEFINITIONS ::= BEGIN

    IMPORTS
        compaq                  FROM CPQHOST-MIB
        enterprises             FROM RFC1155-SMI
        Counter                 FROM RFC1155-SMI
        Gauge                   FROM RFC1155-SMI
        DisplayString           FROM RFC1213-MIB
        OBJECT-TYPE             FROM RFC-1212
        TRAP-TYPE               FROM RFC-1215
        sysName                 FROM RFC1213-MIB
        cpqHoTrapFlags          FROM CPQHOST-MIB;

--    compaq               OBJECT IDENTIFIER ::= { enterprises 232 }

    cpqSasSwitch           OBJECT IDENTIFIER ::= { compaq 25 }
    cpqSasSwitchMibRev     OBJECT IDENTIFIER ::= { cpqSasSwitch 1 }
    cpqSasSwitchComponent  OBJECT IDENTIFIER ::= { cpqSasSwitch 2 }

    cpqSasSwitchInterface  OBJECT IDENTIFIER ::= { cpqSasSwitchComponent 1 }
    cpqSasSwitchHw         OBJECT IDENTIFIER ::= { cpqSasSwitchComponent 2 }

    cpqSasSwitchOsCommon   OBJECT IDENTIFIER ::= { cpqSasSwitchInterface 4 }

    cpqSasSwitchHwType     OBJECT IDENTIFIER ::= { cpqSasSwitchHw 1 }


-- ****************************************************************************
--   SAS Switch MIB Revision
--  =================================
--
-- The compaq enterprise               (1.3.6.1.4.1.232)
--      cpqSasSwitch Group             (1.3.6.1.4.1.232.25)
--       cpqSasSwitchMibRev Group      (1.3.6.1.4.1.232.25.1)
--
--      An SNMP agent conforming to this document will return a
--      cpqSasSwitchMibRevMajor of one (1) and a cpqSasSwitchMibRevMinor of
--      zero (0).
-- :CPQ,DEV:
--      MIB Rev of 1.0 is for the first release.
-- :CPQ,ENDDEV:
--
--      Implementation of the cpqSasSwitchMibRev group is mandatory for
--      all agents supporting the SAS Switch MIB.
--
--
-- ****************************************************************************

    cpqSasSwitchMibRevMajor OBJECT-TYPE
        SYNTAX  INTEGER (1..65535)
        ACCESS  read-only
        STATUS  mandatory
        DESCRIPTION
            "The Major Revision level.
             A change in the major revision level represents a major change
             in the architecture of the MIB.  A change in the major revision
             level may indicate a significant change in the information
             supported and/or the meaning of the supported information,
             correct interpretation of data may require a MIB document with
             the same major revision level."
        ::= { cpqSasSwitchMibRev 1 }

    cpqSasSwitchMibRevMinor OBJECT-TYPE
        SYNTAX  INTEGER (0..65535)
        ACCESS  read-only
        STATUS  mandatory
        DESCRIPTION
            "The Minor Revision level.
             A change in the minor revision level may represent some minor
             additional support, no changes to any pre-existing information
             has occurred."
        ::= { cpqSasSwitchMibRev 2 }

    cpqSasSwitchMibCondition OBJECT-TYPE
        SYNTAX  INTEGER {
            other(1),
            ok(2),
            degraded(3),
            failed(4)
            }
        ACCESS  read-only
        STATUS  mandatory
        DESCRIPTION
            "The overall condition (status) of the system represented by
            this MIB."
        ::= { cpqSasSwitchMibRev 3 }


-- ****************************************************************************
--    SAS Switch Hardware Group
--    =========================
--
-- The compaq enterprise               (1.3.6.1.4.1.232)
--      cpqSasSwitch Group             (1.3.6.1.4.1.232.25)
--       cpqSasSwitchComponent Group   (1.3.6.1.4.1.232.25.2)
--        cpqSasSwitchHw Group         (1.3.6.1.4.1.232.25.2.2)
--
--      The cpqSasSwitchHw group contains configuration and statistical
--      information about the SAS Switch hardware.
--
--      Implementation of the cpqSasSwitchHw group is mandatory for all
--      agents that support the SAS Switch MIB.
--
-- ****************************************************************************


-- ****************************************************************************
--    SAS Switch Type
--    ===============
--
-- The compaq enterprise               (1.3.6.1.4.1.232)
--      cpqSasSwitch Group             (1.3.6.1.4.1.232.25)
--       cpqSasSwitchComponent Group   (1.3.6.1.4.1.232.25.2)
--        cpqSasSwitchHw Group         (1.3.6.1.4.1.232.25.2.2)
--         cpqSasSwitchHwType          (1.3.6.1.4.1.232.25.2.2.1)
--
--  The cpqSasSwitchHwType contains object identifiers unique to each
--  SAS Switch type.
--
-- ****************************************************************************


--   The SysObjId for the "HP Virtual SAS Manager (VSM) Module" is
--   (1.3.6.1.4.1.232.25.2.2.1.1)
--   cpqSasSwitchTypeVsmm  OBJECT IDENTIFIER ::= { cpqSasSwitchHwType 1 }



END
