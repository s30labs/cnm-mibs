Novell-LANalyzer-Ext-MIB DEFINITIONS ::= BEGIN

-- Title:  LANtern RMON+ Extensions MIB Version 1.0
-- Date:   October 15, 1992

	IMPORTS
		enterprises, TimeTicks, IpAddress, Counter, Gauge
			FROM RFC1155-SMI
		DisplayString
			FROM RFC1213-MIB

		rmon, alarmIndex, alarmVariable, alarmSampleType,
		alarmValue, alarmRisingThreshold, alarmFallingThreshold,
		channelIndex, channelMatches, channelDescription,
        	OwnerString, EntryStatus       	   
			FROM RFC1271-MIB		
		TRAP-TYPE
			FROM RFC-1215
		OBJECT-TYPE
			FROM RFC-1212;


novell			OBJECT IDENTIFIER ::= { enterprises 23 }

productType		OBJECT IDENTIFIER ::= { novell 1 }
mibDoc			OBJECT IDENTIFIER ::= { novell 2 }

lantern			OBJECT IDENTIFIER ::= { productType 1 }
lantern-rmonPlus	OBJECT IDENTIFIER ::= { lantern 3 }

rmonPlus-mib		OBJECT IDENTIFIER ::= { mibDoc 13 }

rmonShadow		OBJECT IDENTIFIER ::= { rmonPlus-mib 1 }
rmonExtensions		OBJECT IDENTIFIER ::= { rmonPlus-mib 2 }

rpAlarm			OBJECT IDENTIFIER ::= { rmonShadow 3 }
rpHosts			OBJECT IDENTIFIER ::= { rmonShadow 4 }
rpMatrix		OBJECT IDENTIFIER ::= { rmonShadow 6 }
rpFilter		OBJECT IDENTIFIER ::= { rmonShadow 7 }
rpBuffer		OBJECT IDENTIFIER ::= { rmonShadow 8 }

rpAdmin			OBJECT IDENTIFIER ::= { rmonExtensions 1 }
rpHostMonitor		OBJECT IDENTIFIER ::= { rmonExtensions 2 }
rpDuplicateIp		OBJECT IDENTIFIER ::= { rmonExtensions 3 }
rpMacToIp		OBJECT IDENTIFIER ::= { rmonExtensions 4 }



--The rmonShadow group contains the tables: rpAlarmTable, rpHostTable,
--rpHostTimeTable, rpMatrixSDTable, rpFilterTable, rpChannelTable and
--rpBufferTable.
--These are extensions to similarly named tables in the RMON MIB.


--
--Alarm table extensions.
--

rpAlarmTable	OBJECT-TYPE
	SYNTAX	SEQUENCE OF RpAlarmEntry
	ACCESS	not-accessible
	STATUS	mandatory
	DESCRIPTION
		"A list of alarm entries that extends the RMON MIB."
	::= { rpAlarm 1 }

rpAlarmEntry	OBJECT-TYPE
	SYNTAX	RpAlarmEntry
	ACCESS	not-accessible
	STATUS	mandatory
	DESCRIPTION
		"A list of parameters that extends the alarm entries
		in RMON."
	INDEX { rpAlarmIndex }
	::= { rpAlarmTable 1 }

RpAlarmEntry ::= SEQUENCE {
	rpAlarmIndex			INTEGER (1..65535),
	rpAlarmRisingDescription	DisplayString (SIZE (0..127)),
	rpAlarmFallingDescription	DisplayString (SIZE (0..127))
}

rpAlarmIndex OBJECT-TYPE
	SYNTAX	INTEGER (1..65535)
	ACCESS	read-only
	STATUS	mandatory
	DESCRIPTION
		"An index that uniquely identifies an entry in the
		rpAlarmTable."
	::= { rpAlarmEntry 1 }

rpAlarmRisingDescription OBJECT-TYPE
	SYNTAX DisplayString (SIZE (0..127))
	ACCESS read-write
	STATUS mandatory
	DESCRIPTION
		"A description of the rising alarm."
	::= { rpAlarmEntry 2 }

rpAlarmFallingDescription OBJECT-TYPE
	SYNTAX DisplayString (SIZE (0..127))
	ACCESS read-write
	STATUS mandatory
	DESCRIPTION
		"A description of the falling alarm."
	::= { rpAlarmEntry 3 }


--
--Host table extensions.
--
rpHostTable	OBJECT-TYPE
	SYNTAX	SEQUENCE OF RpHostEntry
	ACCESS	not-accessible
	STATUS	mandatory
	DESCRIPTION
		"A list of host entries that extends the RMON MIB."
	::= { rpHosts 2 }

rpHostEntry	OBJECT-TYPE
	SYNTAX	RpHostEntry
	ACCESS	not-accessible
	STATUS	mandatory
	DESCRIPTION
		"A collection of statistics that extend the host entries
		in RMON."
	INDEX { rpHostIndex, rpHostAddress }
	::= { rpHostTable 1 }

RpHostEntry ::= SEQUENCE {
	rpHostAddress		OCTET STRING,
	rpHostCreationOrder	INTEGER (1..65535),
	rpHostIndex		INTEGER (1..65535),
	rpHostProtocols		INTEGER,
	rpHostFirstTransmit	TimeTicks,
	rpHostLastTransmit	TimeTicks
}

rpHostAddress OBJECT-TYPE
	SYNTAX OCTET STRING
	ACCESS read-only
	STATUS mandatory
	DESCRIPTION
		"The physical address of this host."
	::= { rpHostEntry 1 }

rpHostCreationOrder OBJECT-TYPE
	SYNTAX INTEGER (1..65535)
	ACCESS read-only
	STATUS mandatory
	DESCRIPTION
		"See hostCreationOrder in the RMON MIB."
	::= { rpHostEntry 2 }

rpHostIndex OBJECT-TYPE
	SYNTAX INTEGER (1..65535)
	ACCESS read-only
	STATUS mandatory
	DESCRIPTION
		"See hostIndex in the RMON MIB."
	::= { rpHostEntry 3 }

rpHostProtocols OBJECT-TYPE
	SYNTAX INTEGER
	ACCESS read-only
	STATUS mandatory
	DESCRIPTION
		"A bit array where each bit indicates a protocol
		that was seen in a good packet transmitted by that host.
		The protocols currently monitored are:

		Bit  Protocol
		2^0  Unrecognized protocol (none of the following)
		2^1  Internet (IP, ARP, RARP)
		2^2  ISO
		2^3  DEC
		2^4  NetWare
		2^5  AppleTalk (AppleTalk, AppleTalk ARP)
		2^6  XNS
		2^7  SNA
		2^8  VINES
		2^9  NetBEUI
		2^10 Media Access Control

		A value of 0 means that no transmission has been
		registered."
	::= { rpHostEntry 4 }

rpHostFirstTransmit OBJECT-TYPE
	SYNTAX TimeTicks
	ACCESS read-only
	STATUS mandatory
	DESCRIPTION
		"The value of sysUpTime when the first good
		transmission by this host occurred.  If this
		value is 0 and the hostOutPkts count is 0 then
		the host has not yet transmitted."

	DEFVAL { 0 }
	::= { rpHostEntry 5 }

rpHostLastTransmit OBJECT-TYPE
	SYNTAX TimeTicks
	ACCESS read-only
	STATUS mandatory
	DESCRIPTION
		"The value of sysUpTime when the most recent
		transmission by this host occurred."
	DEFVAL { 0 }
	::= { rpHostEntry 6 }

--
--HostTime table extensions.
--
rpHostTimeTable	OBJECT-TYPE
	SYNTAX	SEQUENCE OF RpHostTimeEntry
	ACCESS	not-accessible
	STATUS	mandatory
	DESCRIPTION
		"A list of host entries that extends the RMON MIB."
	::= { rpHosts 3 }

rpHostTimeEntry	OBJECT-TYPE
	SYNTAX	RpHostTimeEntry
	ACCESS	not-accessible
	STATUS	mandatory
	DESCRIPTION
		"A collection of statistics that extend the host entries
		in RMON."
	INDEX { rpHostTimeIndex, rpHostTimeCreationOrder }
	::= { rpHostTimeTable 1 }

RpHostTimeEntry ::= SEQUENCE {
	rpHostTimeAddress  	OCTET STRING,
	rpHostTimeCreationOrder	INTEGER (1..65535),
	rpHostTimeIndex		INTEGER (1..65535),
	rpHostTimeProtocols	INTEGER,
	rpHostTimeFirstTransmit	TimeTicks,
	rpHostTimeLastTransmit	TimeTicks
}

rpHostTimeAddress OBJECT-TYPE
	SYNTAX OCTET STRING
	ACCESS read-only
	STATUS mandatory
	DESCRIPTION
		"The physical address of this host."
	::= { rpHostTimeEntry 1 }

rpHostTimeCreationOrder OBJECT-TYPE
	SYNTAX INTEGER (1..65535)
	ACCESS read-only
	STATUS mandatory
	DESCRIPTION
		"See hostTimeCreationOrder in the RMON MIB."
	::= { rpHostTimeEntry 2 }

rpHostTimeIndex OBJECT-TYPE
	SYNTAX INTEGER (1..65535)
	ACCESS read-only
	STATUS mandatory
	DESCRIPTION
		"See hostIndex in the RMON MIB."
	::= { rpHostTimeEntry 3 }

rpHostTimeProtocols OBJECT-TYPE
	SYNTAX INTEGER
	ACCESS read-only
	STATUS mandatory
	DESCRIPTION
		"A bit array where each bit indicates a protocol that
		was seen in a good packet transmitted by that host.
		The protocols currently monitored are:

		Bit  Protocol
		2^0  Unrecognized protocol (none of the following)
		2^1  Internet (IP, ARP, RARP)
		2^2  ISO
		2^3  DEC
		2^4  NetWare
		2^5  AppleTalk (AppleTalk, AppleTalk ARP)
		2^6  XNS
		2^7  SNA
		2^8  VINES
		2^9  NetBEUI
		2^10 Media Access Control

		A value of 0 means that no transmission has been
		registered."
	::= { rpHostTimeEntry 4 }

rpHostTimeFirstTransmit OBJECT-TYPE
	SYNTAX TimeTicks
	ACCESS read-only
	STATUS mandatory
	DESCRIPTION
		"The value of sysUpTime when the first good
		transmission by this host occurred.  If this
		value is 0 and the hostOutPkts count is 0 then
		the host has not yet transmitted."

	DEFVAL { 0 }
	::= { rpHostTimeEntry 5 }

rpHostTimeLastTransmit OBJECT-TYPE
	SYNTAX TimeTicks
	ACCESS read-only
	STATUS mandatory
	DESCRIPTION
		"The value of sysUpTime when the most recent
		transmission by this host occurred."
	DEFVAL { 0 }
	::= { rpHostTimeEntry 6 }

--
--Matrix table extensions.
--
--This includes rpMatrixSDTable and rpMatrixDSTable

rpMatrixSDTable	OBJECT-TYPE
	SYNTAX	SEQUENCE OF RpMatrixSDEntry
	ACCESS	not-accessible
	STATUS	mandatory
	DESCRIPTION
		"A list of matrix entries that extends the RMON MIB."
	::= { rpMatrix 2 }

rpMatrixSDEntry	OBJECT-TYPE
	SYNTAX	RpMatrixSDEntry
	ACCESS	not-accessible
	STATUS	mandatory
	DESCRIPTION
		"A collection of statistics that extend the matrix entries
		in RMON."
	INDEX { rpMatrixSDIndex,
		rpMatrixSDSourceAddress, rpMatrixSDDestAddress }
	::= { rpMatrixSDTable 1 }

RpMatrixSDEntry ::= SEQUENCE {
	rpMatrixSDSourceAddress	OCTET STRING,
	rpMatrixSDDestAddress	OCTET STRING,
	rpMatrixSDIndex		INTEGER (1..65535),
	rpMatrixSDProtocols	INTEGER,
	rpMatrixSDFirstTransmit	TimeTicks,
	rpMatrixSDLastTransmit	TimeTicks
}

rpMatrixSDSourceAddress OBJECT-TYPE
	SYNTAX OCTET STRING
	ACCESS read-only
	STATUS mandatory
	DESCRIPTION
		"The source physical address."
	::= { rpMatrixSDEntry 1 }

rpMatrixSDDestAddress OBJECT-TYPE
	SYNTAX OCTET STRING
	ACCESS read-only
	STATUS mandatory
	DESCRIPTION
		"The destination physical address."
	::= { rpMatrixSDEntry 2 }

rpMatrixSDIndex OBJECT-TYPE
	SYNTAX INTEGER (1..65535)
	ACCESS read-only
	STATUS mandatory
	DESCRIPTION
		"See matrixSDIndex in the RMON MIB."
	::= { rpMatrixSDEntry 3 }

rpMatrixSDProtocols OBJECT-TYPE
	SYNTAX INTEGER
	ACCESS read-only
	STATUS mandatory
	DESCRIPTION
		"A bit array where each bit indicates a protocol
		that was seen in a good packet transmitted from
		rpMatrixSDSourceAddress to rpMatrixSDDestAddress.
		The protocols currently monitored are:

		Bit  Protocol
		2^0  Unrecognized protocol (none of the following)
		2^1  Internet (IP, ARP, RARP)
		2^2  ISO
		2^3  DEC
		2^4  NetWare
		2^5  AppleTalk (AppleTalk, AppleTalk ARP)
		2^6  XNS
		2^7  SNA
		2^8  VINES
		2^9  NetBEUI
		2^10 Media Access Control"

	::= { rpMatrixSDEntry 4 }

rpMatrixSDFirstTransmit OBJECT-TYPE
	SYNTAX TimeTicks
	ACCESS read-only
	STATUS mandatory
	DESCRIPTION
		"The value of sysUpTime when the first good
		transmission from rpMatrixSDSourceAddress to
		rpMatrixSDDestAddress occurred."
	::= { rpMatrixSDEntry 5 }

rpMatrixSDLastTransmit OBJECT-TYPE
	SYNTAX TimeTicks
	ACCESS read-only
	STATUS mandatory
	DESCRIPTION
		"The value of sysUpTime when the most recent
		transmission from rpMatrixSDSourceAddress to
		rpMatrixSDDestAddress occurred."
	::= { rpMatrixSDEntry 6 }



--Matrix Destination to Source table extension.


rpMatrixDSTable	OBJECT-TYPE
	SYNTAX	SEQUENCE OF RpMatrixDSEntry
	ACCESS	not-accessible
	STATUS	mandatory
	DESCRIPTION
		"A list of matrix entries that extends the RMON MIB."
	::= { rpMatrix 3 }

rpMatrixDSEntry	OBJECT-TYPE
	SYNTAX	RpMatrixDSEntry
	ACCESS	not-accessible
	STATUS	mandatory
	DESCRIPTION
		"A collection of statistics that extend the matrix entries
		in RMON."
	INDEX { rpMatrixDSIndex,
		rpMatrixDSDestAddress, rpMatrixDSSourceAddress }
	::= { rpMatrixDSTable 1 }

RpMatrixDSEntry ::= SEQUENCE {
	rpMatrixDSSourceAddress	OCTET STRING,
	rpMatrixDSDestAddress	OCTET STRING,
	rpMatrixDSIndex		INTEGER (1..65535),
	rpMatrixDSProtocols	INTEGER,
	rpMatrixDSFirstTransmit	TimeTicks,
	rpMatrixDSLastTransmit	TimeTicks
}

rpMatrixDSSourceAddress OBJECT-TYPE
	SYNTAX OCTET STRING
	ACCESS read-only
	STATUS mandatory
	DESCRIPTION
		"The source physical address."
	::= { rpMatrixDSEntry 1 }

rpMatrixDSDestAddress OBJECT-TYPE
	SYNTAX OCTET STRING
	ACCESS read-only
	STATUS mandatory
	DESCRIPTION
		"The destination physical address."
	::= { rpMatrixDSEntry 2 }

rpMatrixDSIndex OBJECT-TYPE
	SYNTAX INTEGER (1..65535)
	ACCESS read-only
	STATUS mandatory
	DESCRIPTION
		"See matrixDSIndex in the RMON MIB."
	::= { rpMatrixDSEntry 3 }

rpMatrixDSProtocols OBJECT-TYPE
	SYNTAX INTEGER
	ACCESS read-only
	STATUS mandatory
	DESCRIPTION
		"A bit array where each bit indicates a protocol
		that was seen in a good packet transmitted from
		rpMatrixDSSourceAddress to rpMatrixDSDestAddress.
		The protocols currently monitored are:

		Bit  Protocol
		2^0  Unrecognized protocol (none of the following)
		2^1  Internet (IP, ARP, RARP)
		2^2  ISO
		2^3  DEC
		2^4  NetWare
		2^5  AppleTalk (AppleTalk, AppleTalk ARP)
		2^6  XNS
		2^7  SNA
		2^8  VINES
		2^9  NetBEUI
		2^10 Media Access Control"

	::= { rpMatrixDSEntry 4 }

rpMatrixDSFirstTransmit OBJECT-TYPE
	SYNTAX TimeTicks
	ACCESS read-only
	STATUS mandatory
	DESCRIPTION
		"The value of sysUpTime when the first good
		transmission from rpMatrixDSSourceAddress to
		rpMatrixDSDestAddress occurred."
	::= { rpMatrixDSEntry 5 }

rpMatrixDSLastTransmit OBJECT-TYPE
	SYNTAX TimeTicks
	ACCESS read-only
	STATUS mandatory
	DESCRIPTION
		"The value of sysUpTime when the most recent
		transmission from rpMatrixDSSourceAddress to
		rpMatrixDSDestAddress occurred."
	::= { rpMatrixDSEntry 6 }


--
-- Filter table extensions.
--

rpFilterTable	OBJECT-TYPE
	SYNTAX	SEQUENCE OF RpFilterEntry
	ACCESS	not-accessible
	STATUS	mandatory
	DESCRIPTION
		"A list of filter entries that extends the RMON MIB."
	::= { rpFilter 1 }

rpFilterEntry	OBJECT-TYPE
	SYNTAX	RpFilterEntry
	ACCESS	not-accessible
	STATUS	mandatory
	DESCRIPTION
		"A collection of objects that extend the filter entries
		in RMON."
	INDEX { rpFilterIndex }
	::= { rpFilterTable 1 }

RpFilterEntry ::= SEQUENCE {
	rpFilterIndex		INTEGER (1..65535),
	rpFilterProtocols	INTEGER
}

rpFilterIndex OBJECT-TYPE
	SYNTAX INTEGER (1..65535)
	ACCESS read-only
	STATUS mandatory
	DESCRIPTION
		"See filterIndex in the RMON MIB."
	::= { rpFilterEntry 1 }

rpFilterProtocols OBJECT-TYPE
	SYNTAX	INTEGER
	ACCESS	read-write
	STATUS	mandatory
	DESCRIPTION
		"This object is a bit mask that identifies the protocol
		suite(s) that match this filter.  The currently defined
		bits are:

		Bit  Protocol
		2^0  Unrecognized protocol (none of the following)
		2^1  Internet (IP, ARP, RARP)
		2^2  ISO
		2^3  DEC
		2^4  NetWare
		2^5  AppleTalk (AppleTalk, AppleTalk ARP)
		2^6  XNS
		2^7  SNA
		2^8  VINES
		2^9  NetBEUI
		2^10 Media Access Control

		The default is -1 (all bits set) which means match
		any protocol.

		This object may not be modified if the associated
		filterStatus is equal to valid(1)."
	DEFVAL { -1 }
	::= { rpFilterEntry 2 }

--
-- Channel table extensions.
--

rpChannelTable	OBJECT-TYPE
	SYNTAX	SEQUENCE OF RpChannelEntry
	ACCESS	not-accessible
	STATUS	mandatory
	DESCRIPTION
		"A list of channel entries that extends the RMON MIB."
	::= { rpFilter 2 }

rpChannelEntry	OBJECT-TYPE
	SYNTAX	RpChannelEntry
	ACCESS	not-accessible
	STATUS	mandatory
	DESCRIPTION
		"A collection of objects that extend the channel entries
		in the RMON MIB."
	INDEX { rpChannelIndex }
	::= { rpChannelTable 1 }

RpChannelEntry ::= SEQUENCE {
	rpChannelIndex			INTEGER (1..65535),
	rpChannelMatchOctets		Counter,
	rpChannelControlBufferFull	INTEGER (0..1)
}

rpChannelIndex OBJECT-TYPE
	SYNTAX INTEGER (1..65535)
	ACCESS read-only
	STATUS mandatory
	DESCRIPTION
		"See channelIndex in the RMON MIB."
	::= { rpChannelEntry 1 }

rpChannelMatchOctets OBJECT-TYPE
	SYNTAX Counter
	ACCESS read-only
	STATUS mandatory
	DESCRIPTION
		"The number of octets (excluding framing bits but including
		FCS octets) in packets which increment the channelMatches
		object in the RMON MIB."
	::= { rpChannelEntry 2 }

rpChannelControlBufferFull OBJECT-TYPE
	SYNTAX INTEGER (0..1) 
	ACCESS read-write
	STATUS mandatory
	DESCRIPTION
		"When this object is set to 1 and the bufferControlFullStatus
                 is full and the bufferControlFullAction is set to 
                 lockWhenFull, this channel will stop monitoring the incomming
                 packet."
	DEFVAL { 0 }
	::= { rpChannelEntry 3 }

--
-- Buffer Control table extensions.
--

rpBufferControlTable	OBJECT-TYPE
	SYNTAX	SEQUENCE OF RpBufferControlEntry
	ACCESS	not-accessible
	STATUS	mandatory
	DESCRIPTION
		"A list of buffer entries that extends the RMON MIB."
	::= { rpBuffer 1 }

rpBufferControlEntry	OBJECT-TYPE
	SYNTAX	RpBufferControlEntry
	ACCESS	not-accessible
	STATUS	mandatory
	DESCRIPTION
		"A collection of objects that extend the buffer entries
		in the RMON MIB."
	INDEX { rpBufferControlIndex }
	::= { rpBufferControlTable 1 }

RpBufferControlEntry ::= SEQUENCE {
	rpBufferControlIndex		INTEGER (1..65535),
	rpBufferCaptureOctets		INTEGER
}

rpBufferControlIndex OBJECT-TYPE
	SYNTAX INTEGER (1..65535)
	ACCESS read-only
	STATUS mandatory
	DESCRIPTION
		"See bufferControlIndex in the RMON MIB."
	::= { rpBufferControlEntry 1 }

rpBufferCaptureOctets OBJECT-TYPE
	SYNTAX INTEGER
	ACCESS read-only
	STATUS mandatory
	DESCRIPTION
		"The number of octets (excluding framing bits but including
		FCS octets and overhead) in packets which are captured in the 
		buffer." 
	::= { rpBufferControlEntry 2 }

-- The Administration Group

-- Implementation of the Administation group is mandatory
--
-- The Administation group contains information to identify
-- this probe.


rpAdminSerialNumber OBJECT-TYPE
	SYNTAX  OCTET STRING
	ACCESS	read-only
	STATUS	mandatory
	DESCRIPTION
		"An ASCII string specifying the serial number
		for this probe."
	::= { rpAdmin 1 }

rpAdminProbeCopies OBJECT-TYPE
	SYNTAX	INTEGER (0..65535)
	ACCESS	read-only
	STATUS	mandatory
	DESCRIPTION
		"The number of copies of a probe with
		rpAdminSerialNumber that can reside on
		a network.

		A value of 0 means unlimited copies."
	DEFVAL { 1 }
	::= { rpAdmin 2 }


-- The Host Monitor Group

-- Implementation of the Host Monitor group is optional
--
-- The Host Monitor group requires the implementation of the Host group.
--
-- The Host Monitor group monitors a set of hosts for a particular
-- host table and sets traps when a host activates or deactivates.


rpHostMonitorControlTable OBJECT-TYPE
	SYNTAX  SEQUENCE OF RpHostMonitorControlEntry
	ACCESS	not-accessible
	STATUS	mandatory
	DESCRIPTION
		"A list of host monitor table control entries."
	::= { rpHostMonitor 1 }


rpHostMonitorControlEntry OBJECT-TYPE
	SYNTAX  RpHostMonitorControlEntry
	ACCESS	not-accessible
	STATUS	mandatory
	DESCRIPTION
		"A list of parameters used to monitor the
		activity of a host."
	INDEX { rpHostMonitorControlIndex }
	::= { rpHostMonitorControlTable 1 }

RpHostMonitorControlEntry ::= SEQUENCE {
	rpHostMonitorControlIndex      		INTEGER (1..65535),
	rpHostMonitorControlHostIndex		INTEGER (1..65535),
	rpHostMonitorControlActiveEvent		INTEGER (0..65535),
	rpHostMonitorControlInactiveEvent	INTEGER (0..65535),
	rpHostMonitorControlTimeout		INTEGER (0..60),
	rpHostMonitorControlOwner		OwnerString,
	rpHostMonitorControlStatus		INTEGER
}

rpHostMonitorControlIndex OBJECT-TYPE
	SYNTAX	INTEGER (1..65535)
	ACCESS	read-only
	STATUS	mandatory
	DESCRIPTION
		"An index that uniquely identifies an entry in the
		rpHostMonitorControlTable."
	::= { rpHostMonitorControlEntry 1 }


rpHostMonitorControlHostIndex OBJECT-TYPE
	SYNTAX	INTEGER (1..65535)
	ACCESS	read-write
	STATUS	mandatory
	DESCRIPTION
		"The host table identified by a particular value
		of this index is associated with the same host table
		as identified by the same value of hostIndex.

		This object may not be modified if the associated
		
rpHostMonitorControlStatus is equal to valid(1)."
	::= { rpHostMonitorControlEntry 2 }

rpHostMonitorControlActiveEvent OBJECT-TYPE
	SYNTAX	INTEGER (0..65535)
	ACCESS	read-write
	STATUS	mandatory
	DESCRIPTION
		"The index of the eventEntry that is used when
		a host monitor entry goes from inactive to active.

		This object may not be modified if the associated
		rpHostMonitorControlStatus is equal to valid(1)."
	::= { rpHostMonitorControlEntry 3 }

rpHostMonitorControlInactiveEvent OBJECT-TYPE
	SYNTAX	INTEGER (0..65535)
	ACCESS	read-write
	STATUS	mandatory
	DESCRIPTION
		"The index of the eventEntry that is used when
		a host monitor entry goes from active to inactive.

		This object may not be modified if the associated
		rpHostMonitorControlStatus is equal to valid(1)."
	::= { rpHostMonitorControlEntry 4 }

rpHostMonitorControlTimeout OBJECT-TYPE
	SYNTAX	INTEGER (0..60)
	ACCESS	read-write
	STATUS	mandatory
	DESCRIPTION
		"The amount of time in minutes a host is allowed to
		be inactive before it is reported to be dead via an
		rpHostInactive trap.  Subsequent traps will not be sent
		for the same host until the host has transmitted a packet
		and timed-out again.

		A value of 0 disables the monitoring of this table."
	DEFVAL { 0 }
	::= { rpHostMonitorControlEntry 5 }

rpHostMonitorControlOwner OBJECT-TYPE
	SYNTAX	OwnerString
	ACCESS	read-write
	STATUS	mandatory
	DESCRIPTION
		"The entity that configured this entry and is
		therefore using the resources assigned to it."
	::= { rpHostMonitorControlEntry 6 }

rpHostMonitorControlStatus OBJECT-TYPE
	SYNTAX	EntryStatus
	ACCESS	read-write
	STATUS	mandatory
	DESCRIPTION
		"The status of this rpHostMonitorControlEntry."
	::= { rpHostMonitorControlEntry 7 }

rpHostMonitorTable OBJECT-TYPE
	SYNTAX	SEQUENCE OF RpHostMonitorEntry
	ACCESS	not-accessible
	STATUS	mandatory
	DESCRIPTION
		"A list of hosts."
	::= { rpHostMonitor 2 }

rpHostMonitorEntry OBJECT-TYPE
	SYNTAX	RpHostMonitorEntry
        ACCESS	not-accessible
	STATUS	mandatory
	DESCRIPTION
		"A collection of information used to monitor a host
		for activity."
	INDEX { rpHostMonitorIndex, rpHostMonitorAddress }
	::= { rpHostMonitorTable 1 }

RpHostMonitorEntry ::= SEQUENCE {
	rpHostMonitorIndex	INTEGER (1..65535),
	rpHostMonitorAddress	OCTET STRING,
	rpHostMonitorActivity	INTEGER,
	rpHostMonitorAddDelete	INTEGER
}

rpHostMonitorIndex OBJECT-TYPE
	SYNTAX INTEGER (1..65535)
	ACCESS read-only
	STATUS mandatory
	DESCRIPTION
		"The host table identified by a particular value
		of this index is associated wth the same host table
		as identified by the same value of hostMonitorControlIndex."
	::= { rpHostMonitorEntry 1 }

rpHostMonitorAddress OBJECT-TYPE
	SYNTAX OCTET STRING
	ACCESS read-only
	STATUS mandatory
	DESCRIPTION
		"The physical address of the monitored host."
	::= { rpHostMonitorEntry 2 }


rpHostMonitorActivity OBJECT-TYPE
	SYNTAX INTEGER {
		active(1),
		inactive(2)
	}
	ACCESS read-only
	STATUS mandatory
	DESCRIPTION
		"The state of the monitored host, initially set to
		active(1).  If an active(1) host has not transmitted
		for rpHostMonitorControlTimeout minutes then the state
		changes to inactive(2).  If an inactive(2) host transmits
		the state changes to active(1)."

	::= { rpHostMonitorEntry 3 }

rpHostMonitorAddDelete OBJECT-TYPE
	SYNTAX INTEGER {
		add(1),
		delete(2)
	}
	ACCESS read-write
	STATUS mandatory
	DESCRIPTION
		"Writing add(1) to this variable will add the
		host specified by the rpHostMonitorAddress index
		to this rpHostMonitorTable.  Writing delete(2) will
		delete the host specified by the rpHostMonitorAddress
		index.

		This object may not be modified if the associated
		rpHostMonitorControlStatus is not equal to valid(1)."
	::= { rpHostMonitorEntry 4 }


-- The Duplicate IP Group

-- Implementation of the Duplicate IP group is optional
--
-- Initially an IP address is associated with a physical address
-- in a host table.  When a packet arrives with this IP but a new
-- physical address, a duplicate IP record is created in the
-- duplicate IP table and a duplicate IP trap is sent.  While the
-- record exists in the table any subsequent packets showing newer
-- mappings will update the record, but no trap will be sent.
-- At the probe's discretion, old records are discarded and the
-- process begins again.


rpDuplicateIpTable OBJECT-TYPE
	SYNTAX	SEQUENCE OF RpDuplicateIpEntry
	ACCESS	not-accessible
	STATUS	mandatory
	DESCRIPTION
		"A list of IP addresses that have duplicate
		physical address."
	::= { rpDuplicateIp 1 }

rpDuplicateIpEntry OBJECT-TYPE
	SYNTAX	RpDuplicateIpEntry
        ACCESS	not-accessible
	STATUS	mandatory
	DESCRIPTION
		"A list of parameters defining an IP address
		with duplicate physical addresses."
	INDEX { rpDuplicateIpAddress }
	::= { rpDuplicateIpTable 1 }

RpDuplicateIpEntry ::= SEQUENCE {
	rpDuplicateIpAddress	IpAddress,
	rpDuplicateIpNewMAC	OCTET STRING,
	rpDuplicateIpOldMAC	OCTET STRING,
	rpDuplicateIpTimestamp	TimeTicks
}

rpDuplicateIpAddress OBJECT-TYPE
	SYNTAX IpAddress
	ACCESS read-only
	STATUS mandatory
	DESCRIPTION
		"The IP address."
	::= { rpDuplicateIpEntry 1 }

rpDuplicateIpNewMAC OBJECT-TYPE
	SYNTAX OCTET STRING
	ACCESS read-only
	STATUS mandatory
	DESCRIPTION
		"The latest physical address associated with the
		IP address in rpDuplicateIPAddress."
	::= { rpDuplicateIpEntry 2 }

rpDuplicateIpOldMAC OBJECT-TYPE
	SYNTAX OCTET STRING
	ACCESS read-only
	STATUS mandatory
	DESCRIPTION
		"The previous physical address associated with
		the IP address in rpDuplicateIPAddress."
	::= { rpDuplicateIpEntry 3 }

rpDuplicateIpTimestamp OBJECT-TYPE
	SYNTAX TimeTicks
	ACCESS read-only
	STATUS mandatory
	DESCRIPTION
		"The value of sysUpTime when this entry was last
		added or updated in the table."
	::= { rpDuplicateIpEntry 4 }


-- The MAC to IP Group

-- Implementation of the MAC to IP group is optional
--
-- The MAC to IP group requires the implementation of the Host group.
--
-- The MAC to IP group keeps records of the IP addresses associated
-- with a host address for an individual host table.


rpMacToIpTable OBJECT-TYPE
	SYNTAX	SEQUENCE OF RpMacToIpEntry
	ACCESS	not-accessible
	STATUS	mandatory
	DESCRIPTION
		"A list of host and IP address pairs."
	::= { rpMacToIp 1 }

rpMacToIpEntry OBJECT-TYPE
	SYNTAX	RpMacToIpEntry
        ACCESS	not-accessible
	STATUS	mandatory
	DESCRIPTION
		"A record defining a host and IP address pair."
	INDEX { rpMacToIpHostIndex,
		rpMacToIpMACAddress, rpMacToIpIPAddress }
	::= { rpMacToIpTable 1 }

RpMacToIpEntry ::= SEQUENCE {
	rpMacToIpHostIndex	INTEGER (1..65535),
	rpMacToIpMACAddress	OCTET STRING,
	rpMacToIpIPAddress	IpAddress
}

rpMacToIpHostIndex OBJECT-TYPE
	SYNTAX	INTEGER (1..65535)
	ACCESS	read-only
	STATUS	mandatory
	DESCRIPTION
		"The host table of which this entry is a part."
	::= { rpMacToIpEntry 1 }

rpMacToIpMACAddress OBJECT-TYPE
	SYNTAX OCTET STRING
	ACCESS read-only
	STATUS mandatory
	DESCRIPTION
		"The physical address of this host."
	::= { rpMacToIpEntry 2 }

rpMacToIpIPAddress OBJECT-TYPE
	SYNTAX IpAddress
	ACCESS read-only
	STATUS mandatory
	DESCRIPTION
		"The IP address of this host."
	::= { rpMacToIpEntry 3 }

          --  Remote Network Monitoring Traps

--
-- RMON Traps
--

risingAlarm TRAP-TYPE
	ENTERPRISE  rmon 
	VARIABLES { alarmIndex, alarmVariable, alarmSampleType,
	            alarmValue, alarmRisingThreshold,
	            rpAlarmRisingDescription }
	DESCRIPTION
		"The SNMP trap that is generated when an alarm
		entry crosses its rising threshold and generates
		an event that is configured for sending SNMP
		traps."
		--Alarm integrator annotation
		--#TYPE "Rising Alarm"
		--#SUMMARY "%s"
		--#ARGUMENTS {5}
		--#SEVERITY CRITICAL
		--#TIMEINDEX 8
		--#HELP "nms.hlp"
		--#HELPTAG 56010
		--#STATE OPERATIONAL
		::= 1

fallingAlarm TRAP-TYPE
	ENTERPRISE  rmon 
	VARIABLES { alarmIndex, alarmVariable, alarmSampleType,
	            alarmValue, alarmFallingThreshold,
	            rpAlarmFallingDescription }
	DESCRIPTION
		"The SNMP trap that is generated when an alarm
		entry crosses its falling threshold and generates
		an event that is configured for sending SNMP
		traps."
		--Alarm integrator annotation
		--#TYPE "Falling Alarm"
		--#SUMMARY "%s"
		--#ARGUMENTS {5}
		--#SEVERITY MAJOR
		--#TIMEINDEX 8
		--#HELP "nms.hlp"
		--#HELPTAG 56011
		--#STATE OPERATIONAL
		::= 2

packetMatch TRAP-TYPE
	ENTERPRISE  rmon 
	VARIABLES { channelIndex, channelMatches, channelDescription }
	DESCRIPTION
		"The SNMP trap that is generated when a packet
		is captured by a channel that is configured for
		 sending SNMP traps."
		--Alarm integrator annotation
		--#TYPE "Packet Match Alarm"
		--#SUMMARY "Channel %d has matched %d packets. %s"
		--#ARGUMENTS {0,1,2}
		--#SEVERITY INFORMATIONAL
		--#TIMEINDEX 8
		--#HELP "nms.hlp"
		--#HELPTAG 56012
		--#STATE OPERATIONAL
		::= 3



--
-- RMON+ Traps
--

rpHostActive TRAP-TYPE
	ENTERPRISE lantern-rmonPlus
	VARIABLES  { rpHostMonitorAddress }
	DESCRIPTION
		"This trap is generated whenever the probe
		first detects that a monitored inactive host
		has begun transmitting again."
              --Alarm integrator annotation
              --#TYPE "Host Active Alarm"
              --#SUMMARY "Station %m has become active"
              --#ARGUMENTS {0}
              --#SEVERITY MAJOR
              --#TIMEINDEX 8
              --#HELP "LSM.HLP"
              --#HELPTAG 56007
              --#STATE OPERATIONAL
              ::= 1


rpHostInactive TRAP-TYPE
	ENTERPRISE lantern-rmonPlus
	VARIABLES  { rpHostMonitorAddress }
	DESCRIPTION
		"This trap is generated whenever the probe
		first detects that a monitored active host
		has not transmitted for the specified interval
		rpHostMonitorControlTimeout."
              --Alarm integrator annotation
              --#TYPE "Host Inactive Alarm"
              --#SUMMARY "Station %m is Inactive"
              --#ARGUMENTS {0}
              --#SEVERITY MAJOR
              --#TIMEINDEX 8
              --#HELP "LSM.HLP"
              --#HELPTAG 56008
              --#STATE OPERATIONAL
              ::= 2

rpDuplicateIpAddr TRAP-TYPE
	ENTERPRISE lantern-rmonPlus
	VARIABLES  { rpDuplicateIpAddress, rpDuplicateIpNewMAC,
			rpDuplicateIpOldMAC }
	DESCRIPTION
		"This trap is generated when the probe detects that
		a host is using an IP address used by another host(s)
		and the IP address is not in the associated
		duplicate IP table."
              --Alarm integrator annotation
              --#TYPE "Duplicate IP Address Alarm"
              --#SUMMARY "Duplicate IP Address %s at Stations %m and %m"
              --#ARGUMENTS {0, 1, 2}
              --#SEVERITY MAJOR
              --#TIMEINDEX 8
              --#HELP "LSM.HLP"
              --#HELPTAG 56009
              --#STATE OPERATIONAL
              ::= 3
END
