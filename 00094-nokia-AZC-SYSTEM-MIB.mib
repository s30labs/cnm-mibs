NOKIA-AZC-SYSTEM-MIB DEFINITIONS ::= BEGIN

-- 4567890123456789012345678901234567890123456789012345678901234567890123456789
-- This line is 80 characters wide, keep lines in this file shorter than that--
-- ===============================================================
--	   Copyright (C) Nokia Corporation 1999
-- ===============================================================
-- This MIB Module defines the System MIB for products running AZC (P020).
-- More detailed description of the variables and tables is
-- provided in other related documentation.
--
-- Format:   SNMP v2 MIB (Simple network management protocol,
--	     version 2, Management Information Base  )
--
-- ================================================================
-- Author      : Raimo Vuonnala
-- Version     : 1.2
-- Created     : 29.12.1999
-- Last Update : 30.12.1999   - Some integers changed to counters
--               04.02.2000   - Added trial attributes
--               13.03.2000   - Added two new attrs
-- ================================================================

IMPORTS

    enterprises
	    FROM RFC1155-SMI
    INTEGER, Gauge32, Counter32
            FROM SNMPv2-SMI
    OBJECT-TYPE
            FROM RFC-1212
    DisplayString, DateAndTime
	    FROM SNMPv2-TC;


nokia			OBJECT IDENTIFIER ::= { enterprises 94}
nokiaProducts		OBJECT IDENTIFIER ::= { nokia 1}
azcProducts             OBJECT IDENTIFIER ::= { nokiaProducts 32 }
azcSystem               OBJECT IDENTIFIER ::= { azcProducts 2 }

azcStatusGroup	OBJECT IDENTIFIER ::= { azcSystem 1}


-- AZC Status Group

        azcVersion OBJECT-TYPE
	SYNTAX DisplayString
	ACCESS read-only
	STATUS mandatory
	DESCRIPTION
		"The version tag of AZC software. "
	::= { azcStatusGroup 1 }


	azcRelease OBJECT-TYPE
	SYNTAX INTEGER
	ACCESS read-only
	STATUS mandatory
	DESCRIPTION
		"The release number of AZC software. "
	::= { azcStatusGroup 2 }


        azcStarted OBJECT-TYPE
        SYNTAX DisplayString
	ACCESS read-only
	STATUS mandatory
	DESCRIPTION
                "The datestamp when AZC software was started. "
        ::= { azcStatusGroup 3 }


        azcLoginsSuccess OBJECT-TYPE
        SYNTAX Counter32
	ACCESS read-only
	STATUS mandatory
	DESCRIPTION
                "The number of successful logins. "
        ::= { azcStatusGroup 4 }


        azcLoginsAuthFailures OBJECT-TYPE
        SYNTAX Counter32
	ACCESS read-only
	STATUS mandatory
	DESCRIPTION
                "The number of logins failed because of
                 authentication failure. "
        ::= { azcStatusGroup 5 }


        azcLoginsACLFailures OBJECT-TYPE
        SYNTAX Counter32
	ACCESS read-only
	STATUS mandatory
	DESCRIPTION
                "The number of logins failed because of
                 ACL subsystem failure. "
        ::= { azcStatusGroup 6 }


        azcLoginsDuplFailures OBJECT-TYPE
        SYNTAX Counter32
	ACCESS read-only
	STATUS mandatory
	DESCRIPTION
                "The number of logins failed because
                 user had already logged on. "
        ::= { azcStatusGroup 7 }


        azcLoginsSpaceFailures OBJECT-TYPE
        SYNTAX Counter32
	ACCESS read-only
	STATUS mandatory
	DESCRIPTION
                "The number of logins failed because
                 maximum number of users already logged on. "
        ::= { azcStatusGroup 8 }


        azcLoginsRADIUSFailures OBJECT-TYPE
        SYNTAX Counter32
	ACCESS read-only
	STATUS mandatory
	DESCRIPTION
                "The number of logins failed because
                 RADIUS system error. "
        ::= { azcStatusGroup 9 }


        azcLoginsRADIUSACLFailures OBJECT-TYPE
        SYNTAX Counter32
	ACCESS read-only
	STATUS mandatory
	DESCRIPTION
                "The number of logins failed because
                 RADIUS ACL error. Currently not used. "
        ::= { azcStatusGroup 10 }


        azcAutologoffsRADIUS OBJECT-TYPE
        SYNTAX Counter32
	ACCESS read-only
	STATUS mandatory
	DESCRIPTION
                "The number of autologoffs because
                 RADIUS of negative accounting response. "
        ::= { azcStatusGroup 11 }


        azcAutologoffsPing OBJECT-TYPE
        SYNTAX Counter32
	ACCESS read-only
	STATUS mandatory
	DESCRIPTION
                "The number of autologoffs because
                 of no response to pings. "
        ::= { azcStatusGroup 12 }


        azcAutologoffsMAC OBJECT-TYPE
        SYNTAX Counter32
	ACCESS read-only
	STATUS mandatory
	DESCRIPTION
                "The number of autologoffs because
                 MAC address of an IP address has been changed. "
        ::= { azcStatusGroup 13 }


        azcAutologoffsACL OBJECT-TYPE
        SYNTAX Counter32
	ACCESS read-only
	STATUS mandatory
	DESCRIPTION
                "The number of autologoffs because
                 ACL error. "
        ::= { azcStatusGroup 14 }


        azcAutologoffsQuota OBJECT-TYPE
        SYNTAX Counter32
	ACCESS read-only
	STATUS mandatory
	DESCRIPTION
                "The number of autologoffs because
                 quota has exceeded. "
        ::= { azcStatusGroup 15 }


        azcAutologoffsMaxTime OBJECT-TYPE
        SYNTAX Counter32
	ACCESS read-only
	STATUS mandatory
	DESCRIPTION
                "The number of autologoffs because
                 maximum time exceeded. "
        ::= { azcStatusGroup 16 }


        azcAutologoffsIdletimer OBJECT-TYPE
        SYNTAX Counter32
	ACCESS read-only
	STATUS mandatory
	DESCRIPTION
                "The number of autologoffs because
                 session has been idle too long time. "
        ::= { azcStatusGroup 17 }


        azcPktsIntIn OBJECT-TYPE
        SYNTAX Counter32
	ACCESS read-only
	STATUS mandatory
	DESCRIPTION
                "The number of packets received
                 from the internal interface. "
        ::= { azcStatusGroup 18 }


        azcPktsIntOut OBJECT-TYPE
        SYNTAX Counter32
	ACCESS read-only
	STATUS mandatory
	DESCRIPTION
                "The number of packets sent
                 to the internal interface. "
        ::= { azcStatusGroup 19 }


        azcBytesIntIn OBJECT-TYPE
        SYNTAX Counter32
	ACCESS read-only
	STATUS mandatory
	DESCRIPTION
                "The number of bytes received
                 from the internal interface. "
        ::= { azcStatusGroup 20 }


        azcBytesIntOut OBJECT-TYPE
        SYNTAX Counter32
	ACCESS read-only
	STATUS mandatory
	DESCRIPTION
                "The number of bytes sent
                 to the internal interface. "
        ::= { azcStatusGroup 21 }

        azcPktsExtIn OBJECT-TYPE
        SYNTAX Counter32
	ACCESS read-only
	STATUS mandatory
	DESCRIPTION
                "The number of packets received
                 from the external interface. "
        ::= { azcStatusGroup 22 }


        azcPktsExtOut OBJECT-TYPE
        SYNTAX Counter32
	ACCESS read-only
	STATUS mandatory
	DESCRIPTION
                "The number of packets sent
                 to the external interface. "
        ::= { azcStatusGroup 23 }


        azcBytesExtIn OBJECT-TYPE
        SYNTAX Counter32
	ACCESS read-only
	STATUS mandatory
	DESCRIPTION
                "The number of bytes received
                 from the external interface. "
        ::= { azcStatusGroup 24 }


        azcBytesExtOut OBJECT-TYPE
        SYNTAX Counter32
	ACCESS read-only
	STATUS mandatory
	DESCRIPTION
                "The number of bytes sent
                 to the external interface. "
        ::= { azcStatusGroup 25 }


        azcPktsNattedIn OBJECT-TYPE
        SYNTAX Counter32
	ACCESS read-only
	STATUS mandatory
	DESCRIPTION
                "The number of packets received and NATed. "
        ::= { azcStatusGroup 26 }


        azcPktsNattedOut OBJECT-TYPE
        SYNTAX Counter32
	ACCESS read-only
	STATUS mandatory
	DESCRIPTION
                "The number of packets sent and NATed."
        ::= { azcStatusGroup 27 }

        azcBytesNattedIn OBJECT-TYPE
        SYNTAX Counter32
	ACCESS read-only
	STATUS mandatory
	DESCRIPTION
                "The number of bytes received and NATed. "
        ::= { azcStatusGroup 28 }


        azcBytesNattedOut OBJECT-TYPE
        SYNTAX Counter32
	ACCESS read-only
	STATUS mandatory
	DESCRIPTION
                "The number of bytes sent and NATed."
        ::= { azcStatusGroup 29 }

        azcPktsNattedErrIn OBJECT-TYPE
        SYNTAX Counter32
	ACCESS read-only
	STATUS mandatory
	DESCRIPTION
                "The number of packets received and NAT failed. "
        ::= { azcStatusGroup 30 }


        azcPktsNattedErrOut OBJECT-TYPE
        SYNTAX Counter32
	ACCESS read-only
	STATUS mandatory
	DESCRIPTION
                "The number of packets sent and NAT failed."
        ::= { azcStatusGroup 31 }

        azcBytesNattedErrIn OBJECT-TYPE
        SYNTAX Counter32
	ACCESS read-only
	STATUS mandatory
	DESCRIPTION
                "The number of bytes received and NAT failed. "
        ::= { azcStatusGroup 32 }


        azcBytesNattedErrOut OBJECT-TYPE
        SYNTAX Counter32
	ACCESS read-only
	STATUS mandatory
	DESCRIPTION
                "The number of bytes sent and NAT failed."
        ::= { azcStatusGroup 33 }


        azcPktsRejInt OBJECT-TYPE
        SYNTAX Counter32
	ACCESS read-only
	STATUS mandatory
	DESCRIPTION
                "The number of packets rejected
                 from the internal interface. "
        ::= { azcStatusGroup 34 }


        azcPktsRejExt OBJECT-TYPE
        SYNTAX Counter32
	ACCESS read-only
	STATUS mandatory
	DESCRIPTION
                "The number of packets rejected
                 from the external interface. "
        ::= { azcStatusGroup 35 }

        azcBytesRejInt OBJECT-TYPE
        SYNTAX Counter32
	ACCESS read-only
	STATUS mandatory
	DESCRIPTION
                "The number of bytes rejected
                 from the internal interface. "
        ::= { azcStatusGroup 36 }


        azcBytesRejExt OBJECT-TYPE
        SYNTAX Counter32
	ACCESS read-only
	STATUS mandatory
	DESCRIPTION
                "The number of bytes rejected
                 from the external interface. "
        ::= { azcStatusGroup 37 }

        azcACLSelectErr OBJECT-TYPE
        SYNTAX Counter32
	ACCESS read-only
	STATUS mandatory
	DESCRIPTION
                "The number of select errors
                 in the ACL module. "
        ::= { azcStatusGroup 38 }


        azcACLSendmsgErr OBJECT-TYPE
        SYNTAX Counter32
	ACCESS read-only
	STATUS mandatory
	DESCRIPTION
                "The number of sendmsg errors
                 in the ACL module. "
        ::= { azcStatusGroup 39 }


        azcACLRevmsgErr OBJECT-TYPE
        SYNTAX Counter32
	ACCESS read-only
	STATUS mandatory
	DESCRIPTION
                "The number of recvmsg errors
                 in the ACL module. "
        ::= { azcStatusGroup 40 }


        azcACLRevmsgOverflow OBJECT-TYPE
        SYNTAX Counter32
	ACCESS read-only
	STATUS mandatory
	DESCRIPTION
                "The number of recvmsg overflows
                 in the ACL module. "
        ::= { azcStatusGroup 41 }


        azcACLSendmsgLocErr OBJECT-TYPE
        SYNTAX Counter32
	ACCESS read-only
	STATUS mandatory
	DESCRIPTION
                "The number of sendmsg errors
                 in the ACL module. "
        ::= { azcStatusGroup 42 }


        azcACLRevmsgLocErr OBJECT-TYPE
        SYNTAX Counter32
	ACCESS read-only
	STATUS mandatory
	DESCRIPTION
                "The number of recvmsg errors
                 in the ACL module. "
        ::= { azcStatusGroup 43 }


        azcACLRevmsgLocOverflow OBJECT-TYPE
        SYNTAX Counter32
	ACCESS read-only
	STATUS mandatory
	DESCRIPTION
                "The number of recvmsg overflows
                 in the ACL module. "
        ::= { azcStatusGroup 44 }

        azcACLRevmsgCtlErr OBJECT-TYPE
        SYNTAX Counter32
	ACCESS read-only
	STATUS mandatory
	DESCRIPTION
                "The number of recvmsg control errors
                 in the ACL module. "
        ::= { azcStatusGroup 45 }

        azcACLRevmsgCtlOverflow OBJECT-TYPE
        SYNTAX Counter32
	ACCESS read-only
	STATUS mandatory
	DESCRIPTION
                "The number of recvmsg control overflows
                 in the ACL module. "
        ::= { azcStatusGroup 46 }


        azcACLMemAllocs OBJECT-TYPE
        SYNTAX Gauge32
	ACCESS read-only
	STATUS mandatory
	DESCRIPTION
                "The number of memory allocations
                 in the ACL module. "
        ::= { azcStatusGroup 47 }


        azcACLMemAllocErr OBJECT-TYPE
        SYNTAX Counter32
	ACCESS read-only
	STATUS mandatory
	DESCRIPTION
                "The number of memory allocation errors
                 in the ACL module. "
        ::= { azcStatusGroup 48 }


        azcActivationKey OBJECT-TYPE
        SYNTAX DisplayString
	ACCESS read-only
	STATUS mandatory
	DESCRIPTION
                "AZC activation key. "
        ::= { azcStatusGroup 49 }


        azcHostID OBJECT-TYPE
        SYNTAX DisplayString
	ACCESS read-only
	STATUS mandatory
	DESCRIPTION
                "AZC host ID. "
        ::= { azcStatusGroup 50 }

        azcIntIf OBJECT-TYPE
        SYNTAX DisplayString
	ACCESS read-only
	STATUS mandatory
	DESCRIPTION
                "AZC internal interface name. "
        ::= { azcStatusGroup 51 }


        azcExtIf OBJECT-TYPE
        SYNTAX DisplayString
	ACCESS read-only
	STATUS mandatory
	DESCRIPTION
                "AZC external interface name. "
        ::= { azcStatusGroup 52 }


        azcMaxTimeout OBJECT-TYPE
        SYNTAX INTEGER
	ACCESS read-only
	STATUS mandatory
	DESCRIPTION
                "AZC max session duration in seconds. "
        ::= { azcStatusGroup 53 }


        azcMaxIdleTimeout OBJECT-TYPE
        SYNTAX INTEGER
	ACCESS read-only
	STATUS mandatory
	DESCRIPTION
                "AZC max session idle time in seconds. "
        ::= { azcStatusGroup 54 }


        azcPingPeriod OBJECT-TYPE
        SYNTAX INTEGER
	ACCESS read-only
	STATUS mandatory
	DESCRIPTION
                "AZC ping period in seconds. "
        ::= { azcStatusGroup 55 }

        azcLoginURL OBJECT-TYPE
        SYNTAX DisplayString
	ACCESS read-only
	STATUS mandatory
	DESCRIPTION
                "AZC login URL. "
        ::= { azcStatusGroup 56 }


        azcIPAddress OBJECT-TYPE
        SYNTAX DisplayString
	ACCESS read-only
	STATUS mandatory
	DESCRIPTION
                "AZC internal IP address. "
        ::= { azcStatusGroup 57 }


        azcExtIPAddress OBJECT-TYPE
        SYNTAX DisplayString
	ACCESS read-only
	STATUS mandatory
	DESCRIPTION
                "AZC external IP address. "
        ::= { azcStatusGroup 58 }


        azcDNSIPAddress OBJECT-TYPE
        SYNTAX DisplayString
	ACCESS read-only
	STATUS mandatory
	DESCRIPTION
                "AZC external DNS proxy IP address. Currently
                 not in use. "
        ::= { azcStatusGroup 59 }

        azcDHCPIPAddress OBJECT-TYPE
        SYNTAX DisplayString
	ACCESS read-only
	STATUS mandatory
	DESCRIPTION
                "AZC DHCP IP Address. "
        ::= { azcStatusGroup 60 }


        azcProxyHost OBJECT-TYPE
        SYNTAX DisplayString
	ACCESS read-only
	STATUS mandatory
	DESCRIPTION
                "AZC HTTP proxy host address. "
        ::= { azcStatusGroup 61 }


        azcProxyPorts OBJECT-TYPE
        SYNTAX DisplayString
	ACCESS read-only
	STATUS mandatory
	DESCRIPTION
                "AZC HTTP proxy ports. "
        ::= { azcStatusGroup 62 }


        azcMailRelayHost OBJECT-TYPE
        SYNTAX DisplayString
	ACCESS read-only
	STATUS mandatory
	DESCRIPTION
                "AZC mail relay host address. "
        ::= { azcStatusGroup 63 }


        azcRADIUSAlivePeriod OBJECT-TYPE
        SYNTAX INTEGER
	ACCESS read-only
	STATUS mandatory
	DESCRIPTION
                "RADIUS accounting-alive period in seconds. "
        ::= { azcStatusGroup 64 }

        azcRADIUSAliveTrigger OBJECT-TYPE
        SYNTAX INTEGER
	ACCESS read-only
	STATUS mandatory
	DESCRIPTION
                "RADIUS accounting-alive trigger size in kilobytes. "
        ::= { azcStatusGroup 65 }


        azcWhitelist OBJECT-TYPE
        SYNTAX DisplayString
	ACCESS read-only
	STATUS mandatory
	DESCRIPTION
                "AZC whitelist host addresses. "
        ::= { azcStatusGroup 66 }


        azcBlackList OBJECT-TYPE
        SYNTAX DisplayString
	ACCESS read-only
	STATUS mandatory
	DESCRIPTION
                "AZC blacklist host addresses. "
        ::= { azcStatusGroup 67 }


        azcDemoAccounts OBJECT-TYPE
        SYNTAX DisplayString
	ACCESS read-only
	STATUS mandatory
	DESCRIPTION
                "AZC demo accounts. "
        ::= { azcStatusGroup 68 }


        azcUDPFilter OBJECT-TYPE
        SYNTAX INTEGER
	ACCESS read-only
	STATUS mandatory
	DESCRIPTION
                "AZC UDP filter setting.
                 Value 1 means that ports > 1024 are protected;
                 value -1 means, that only DHCP and DNS are open;
                 value 0 means, that UDP is totally open;
                 values > 1 means, that UDP port greater than the value are open. "
        ::= { azcStatusGroup 69 }


        azcCutTime OBJECT-TYPE
        SYNTAX DisplayString
	ACCESS read-only
	STATUS mandatory
	DESCRIPTION
                "AZC session cut-time. "
        ::= { azcStatusGroup 70 }


        azcCutSafetyTime OBJECT-TYPE
        SYNTAX INTEGER
	ACCESS read-only
	STATUS mandatory
	DESCRIPTION
                "AZC session-cut safety time tolerance in minutes. "
        ::= { azcStatusGroup 71 }


        azcRADIUSActivated OBJECT-TYPE
        SYNTAX INTEGER {
             disabled(0),
             enabled(1)
             }
	ACCESS read-only
	STATUS mandatory
	DESCRIPTION
                "AZC RADIUS activation state. "
        ::= { azcStatusGroup 72 }


        azcMACCheckMode OBJECT-TYPE
        SYNTAX INTEGER {
             disabled(0),
             enabled(1)
             }
	ACCESS read-only
	STATUS mandatory
	DESCRIPTION
                "AZC MAC address check mode. "
        ::= { azcStatusGroup 73 }


        azcNATState OBJECT-TYPE
        SYNTAX INTEGER {
             disabled(0),
             enabled(1)
             }
	ACCESS read-only
	STATUS mandatory
	DESCRIPTION
                "AZC NAT activation state. "
        ::= { azcStatusGroup 74 }


        azcDHCPState OBJECT-TYPE
        SYNTAX INTEGER {
             disabled(0),
             enabled(1)
             }
	ACCESS read-only
	STATUS mandatory
	DESCRIPTION
                "AZC DHCP activation state. "
        ::= { azcStatusGroup 75 }


        azcSSLState OBJECT-TYPE
        SYNTAX INTEGER {
             disabled(0),
             enabled(1)
             }
	ACCESS read-only
	STATUS mandatory
	DESCRIPTION
                "AZC SSL activation state. "
        ::= { azcStatusGroup 76 }


        azcSNMPTrapState OBJECT-TYPE
        SYNTAX INTEGER {
             disabled(0),
             enabled(1)
             }
	ACCESS read-only
	STATUS mandatory
	DESCRIPTION
                "AZC SNMP trap activation state. "
        ::= { azcStatusGroup 77 }


        azcMACAuthState OBJECT-TYPE
        SYNTAX INTEGER {
             disabled(0),
             enabled(1)
             }
	ACCESS read-only
	STATUS mandatory
	DESCRIPTION
                "AZC MAC authentication state. "
        ::= { azcStatusGroup 78 }


        azcMACRealm OBJECT-TYPE
        SYNTAX DisplayString
	ACCESS read-only
	STATUS mandatory
	DESCRIPTION
                "AZC MAC authentication realm. "
        ::= { azcStatusGroup 79 }


        azcMACPassword OBJECT-TYPE
        SYNTAX DisplayString
	ACCESS read-only
	STATUS mandatory
	DESCRIPTION
                "AZC MAC authenticatoin password. "
        ::= { azcStatusGroup 80 }


        azcNATDArgs OBJECT-TYPE
        SYNTAX DisplayString
	ACCESS read-only
	STATUS mandatory
	DESCRIPTION
                "AZC NAT daemon arguments. "
        ::= { azcStatusGroup 81 }


        azcSyslogFacility OBJECT-TYPE
        SYNTAX INTEGER
	ACCESS read-only
	STATUS mandatory
	DESCRIPTION
                "AZC syslog facility code. "
        ::= { azcStatusGroup 82 }


        azcSyslogLevel OBJECT-TYPE
        SYNTAX INTEGER {
             nothing(0),
             onlyErrors(1),
             alsoWarnings(4),
             alsoInfo(6)
             }
	ACCESS read-only
	STATUS mandatory
	DESCRIPTION
                "AZC syslogging level. "
        ::= { azcStatusGroup 83 }


        azcQOSClass1 OBJECT-TYPE
        SYNTAX DisplayString
	ACCESS read-only
	STATUS mandatory
	DESCRIPTION
                "AZC QOS Class 1 (formatted as 'name rateKBps'). "
        ::= { azcStatusGroup 84 }


        azcQOSClass2 OBJECT-TYPE
        SYNTAX DisplayString
	ACCESS read-only
	STATUS mandatory
	DESCRIPTION
                "AZC QOS Class 2 (formatted as 'name rateKBps'). "
        ::= { azcStatusGroup 85 }


        azcQOSClass3 OBJECT-TYPE
        SYNTAX DisplayString
	ACCESS read-only
	STATUS mandatory
	DESCRIPTION
                "AZC QOS Class 3 (formatted as 'name rateKBps'). "
        ::= { azcStatusGroup 86 }


        azcQOSClassDefault OBJECT-TYPE
        SYNTAX DisplayString
	ACCESS read-only
	STATUS mandatory
	DESCRIPTION
                "AZC default QOS Class (rateKBps). "
        ::= { azcStatusGroup 87 }


        azcLocation OBJECT-TYPE
        SYNTAX DisplayString
	ACCESS read-only
	STATUS mandatory
	DESCRIPTION
                "AZC location string. "
        ::= { azcStatusGroup 88 }



        azcUptime OBJECT-TYPE
        SYNTAX INTEGER
        ACCESS read-only
        STATUS mandatory
        DESCRIPTION
                "Number of seconds since AZC startup. "
        ::= { azcStatusGroup 89 }


        azcTrialTime OBJECT-TYPE
        SYNTAX INTEGER
        ACCESS read-only
        STATUS mandatory
        DESCRIPTION
                "Free trial time in seconds. "
        ::= { azcStatusGroup 90 }


        azcTrialLockime OBJECT-TYPE
        SYNTAX INTEGER
        ACCESS read-only
        STATUS mandatory
        DESCRIPTION
                "Trial lock time in seconds. "
        ::= { azcStatusGroup 91 }


        azcNokiaAuthMode OBJECT-TYPE
        SYNTAX INTEGER
        ACCESS read-only
        STATUS mandatory
        DESCRIPTION
                "Nokia authentication mode. "
        ::= { azcStatusGroup 92 }


        azcActiveLogins OBJECT-TYPE
        SYNTAX INTEGER
        ACCESS read-only
        STATUS mandatory
        DESCRIPTION
                "Number of logged-in users. "
        ::= { azcStatusGroup 93 }

        azcZoneName OBJECT-TYPE
        SYNTAX DisplayString
	ACCESS read-only
	STATUS mandatory
	DESCRIPTION
                "AZC Zone Name. "
        ::= { azcStatusGroup 94 }


        azcLoginTime OBJECT-TYPE
        SYNTAX INTEGER
        ACCESS read-only
        STATUS mandatory
        DESCRIPTION
                "Average login time (response time) in seconds. "
        ::= { azcStatusGroup 95 }




END
